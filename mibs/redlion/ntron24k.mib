NTRON-MIB DEFINITIONS ::= BEGIN

IMPORTS
         MODULE-IDENTITY, OBJECT-TYPE,
         Counter32, Integer32, IpAddress, enterprises FROM SNMPv2-SMI
         DisplayString FROM SNMPv2-TC;

ntron MODULE-IDENTITY
    LAST-UPDATED "201910022012" -- October 02, 2019 3:12 PM (CDT)
    ORGANIZATION "N-Tron Corporation"
    CONTACT-INFO
            "Internet: http://www.redlion.net
             E-Mail:   support@redlion.net"
    DESCRIPTION
            "Enterprises MIB for N-Tron NT24K Product"
    REVISION "201910022012" -- October 02, 2019 3:12 PM (CDT)
    DESCRIPTION
            "Release for NT24k System Firmware 2.2
              - Added ntronLldpGroup
              - Added ntronPortsPortPortUserDescription to ntronPortGroup
              - Added ntronRstpBridgeBpduFlooding option to ntronRstpBridge
              - Updated description for ntronFileTransferActionType"
    REVISION "201808032250Z" -- August 3, 2018 5:50 PM (CDT)
    DESCRIPTION
            "Release for NT24k System Firmware 2.1
              - Added ntronDhcprGroup
              - Added ntronDhcpsGroup
              - Added ntronPortSecurityGroup
              - Added ntronFileTransferConfigKeepOptionsKeepPortSecurity to ntronFileTransferConfigKeepOptions
              - Added ntronFactoryResetOptionsKeepPortSecurity to ntronFactoryResetOptions

"

    REVISION "201711221827Z" -- November 22, 2017 12:27 PM (CST)
    DESCRIPTION
            "Release for NT24k System Firmware 2.0
              - Added ntronTimeConfigTimeSource to ntronTimeConfig
              - Added ntronLocalsecurityGroup.
              - Updated description for ntronSecurityRadiusConfigServerAuthPort
              - Updated description for ntronFileTransferConfigKeepOptionsKeepUser
              - Updated description for ntronFactoryResetOptionsKeepUser
              - Updated description for ntronSecurityRadiusConfigServerSharedSecret"
    REVISION "201705102023Z" -- May 10, 2017 3:23 PM (CDT)
    DESCRIPTION
            "Release for NT24k System Firmware 1.11.6
              - Added ntronEventLogFilterGroup
              - Added ntronFaultConfigFaultEventsTable to ntronFaultConfig
              - Added ntronSyslogConfigGroup
              - Added support for new switch models
              - Updated description for ntronVlanConfigPrimaryMgmtVlanId to fix spelling of DHCP"
    REVISION "201608261902Z" -- August 26, 2016 2:02 PM (CDT)
    DESCRIPTION
            "Release for NT24k System Firmware 1.10.2
              - Added ntronFileTransferConfigKeepOptionsKeepPoe to ntronFileTransferConfigKeepOptions
              - Added ntronFactoryResetOptionsKeepPoe to ntronFactoryResetOptions
              - Added support for new switch model"
    REVISION "201602092006Z" -- February 09, 2016 02:06 PM (CST)
    DESCRIPTION
            "Release for NT24k System Firmware 1.9.2
              - Deprecated ntronSaveConfig.
              - Deprecated ntronIpConfigAddress.
              - Deprecated ntronIpConfigSubnet.
              - Deprecated ntronIpConfigGateway.
              - Deprecated ntronIpConfigFallbackIPAddress.
              - Deprecated ntronIpConfigFallbackSubnet.
              - Deprecated ntronIpConfigFallbackGateway.
              - Added ntronFactoryReset to ntronSystemGroup.
              - Added ntronSystemConfigSysSave to ntronSystemConfig.
              - Added ntronNetworkConfig to ntronIpConfig.
              - Added ntronFileTransfer to ntronSystemConfig.
              - Added ntronSystemConfigBootloaderVersion to ntronSystemGroup.
              - Added ntronSystemBootloaderVersionUponReboot to ntronSystemGroup.
              - Added ntronSystemFirmwareVersionUponReboot to ntronSystemGroup.
              - Improved readability."
    REVISION "201505212300Z"    -- May 21, 2015 6:00 PM (CDT)
    DESCRIPTION
            "Release for NT24k System Firmware 1.8.5
              - Corrected the previous NT24k System Firmware release version listed in the description.
              - Corrected the value of 'no' for ntronPortsPortCrossOver and ntronPortsStatusPortCrossover.
              - Added support for new switch models"
    REVISION "201412182230Z"    -- Dec 18, 2014 4:30 PM (CST)
    DESCRIPTION
            "Release for NT24k System Firmware 1.7.4
              - Added support for Time
              - Added support for SNTP.
              - Added support for 802.1X
              - Added support for RADIUS
              - Added support for Voltage and Current"
    REVISION "201406271827Z"    -- June 27, 2014 01:27 PM (CDT)
    DESCRIPTION
            "Release for NT24k System Firmware 1.6.0
              - Added support for event log enable/disable."
    REVISION "201405012105Z"    -- May 1, 2014 04:05 PM (CDT)
    DESCRIPTION
            "Release for NT24k System Firmware 1.5.1
              - Changed label ntronNringPortSetsPortSetPrtx to ntronNringPortSetsPortSetPortx, to match ntronNringPortSetsPortSetPorty
              - Renamed 'ntronIgmpList' as 'ntronIgmpStatus'
              - Added 'ntronIgmpNringRouterPorts', 'ntronIgmpNLinkRouterPorts' and 'ntronIgmpActiveQuerierIp'
              - Default SNMP MIB Table Leaf functions did not work when key fields were zero-based.
              - Fixed MIBs that were invalid due to a missing comma in an integer enumeration.
              - Changed membership VlanTagged to INTEGER.
              - Added valid range to membership RingNo, PortSetId, and VlanId.
              - Changed access permission for membership RingNo to read only.
              - Added NringStatusState enumeration entry for unknown.
              - Created N-Ring membership OIDs.
              - Corrected acceptable values for N-Ring status OID.
              - Corrected typo."
    REVISION "201308231957Z"    -- Aug 23, 2013 2:57 PM (CDT)
    DESCRIPTION
            "Release for NT24k System Firmware 1.4.4"
    REVISION "201305101924Z"    -- May 10, 2013 2:24 PM (CDT)
    DESCRIPTION
            "Release for NT24k System Firmware 1.3.3
              - changed 'ntronPortsStatsPortPortNumber' OID from read-write to read-only"
    REVISION "201304111753Z"    -- April 11, 2013 12:53 PM (CDT)
    DESCRIPTION
            "Initial Release for NT24k System Firmware 1.3.2"
     ::= {enterprises 28381}

nt24k             			OBJECT IDENTIFIER 	::= {ntron 24000}
ntronSystemGroup			OBJECT IDENTIFIER  	::= {nt24k 100}
ntronFaultGroup  			OBJECT IDENTIFIER	::= {nt24k 300}
ntronIgmpGroup  			OBJECT IDENTIFIER	::= {nt24k 600}
ntronNringGroup  			OBJECT IDENTIFIER	::= {nt24k 900}
ntronNViewGroup  			OBJECT IDENTIFIER	::= {nt24k 1000}
ntronPortGroup  			OBJECT IDENTIFIER	::= {nt24k 1100}
ntronMirrorGroup  			OBJECT IDENTIFIER	::= {nt24k 1200}
ntronTrunkGroup  			OBJECT IDENTIFIER	::= {nt24k 1300}
ntronRateLimitGroup			OBJECT IDENTIFIER	::= {nt24k 1400}
ntronRstpGroup				OBJECT IDENTIFIER	::= {nt24k 1500}
ntronVlanGroup				OBJECT IDENTIFIER	::= {nt24k 1600}
ntronSnmpGroup				OBJECT IDENTIFIER	::= {nt24k 1700}
ntronEventLogGroup			OBJECT IDENTIFIER	::= {nt24k 1800}
ntronTimeGroup				OBJECT IDENTIFIER	::= {nt24k 1900}
ntronTimeSntpGroup			OBJECT IDENTIFIER	::= {nt24k 2000}
ntronSecurityDot1xGroup		OBJECT IDENTIFIER	::= {nt24k 2100}
ntronSecurityRadiusGroup	OBJECT IDENTIFIER	::= {nt24k 2200}
ntronEventLogFilterGroup    OBJECT IDENTIFIER   ::= {nt24k 2300}
ntronSyslogGroup            OBJECT IDENTIFIER   ::= {nt24k 2400}
ntronLocalSecurityGroup     OBJECT IDENTIFIER   ::= {nt24k 2500}

ntronPortSecurityGroup      OBJECT IDENTIFIER   ::= {nt24k 2800}
ntronDhcpsGroup             OBJECT IDENTIFIER   ::= {nt24k 2900}
ntronDhcprGroup             OBJECT IDENTIFIER   ::= {nt24k 3000}
ntronLldpGroup              OBJECT IDENTIFIER   ::= {nt24k 3100}

--  ----------------------------------------------------------------------------------
--
--	SystemGroup
--
--  ----------------------------------------------------------------------------------

--  ----------------------------------------------------------------------------------
ntronSystemConfig   OBJECT IDENTIFIER  	::= {ntronSystemGroup 10}
--  ----------------------------------------------------------------------------------

ntronSystemConfigSysReboot 		OBJECT-TYPE
	SYNTAX          			INTEGER
								{
									switchNoReset (1),
									switchReset   (2)
								}
	MAX-ACCESS 				  	read-write
	STATUS   				   	current
	DESCRIPTION 				"Setting this object to 'switchReset' will cause the switch to
								perform a hardware reset within approximately 4-6 seconds.  Setting
								this object to 'switchNoReset' will have no effect.  The value
								'switchNoReset' will be returned whenever this object is retrieved."
	::= { ntronSystemConfig 1 }

ntronSystemConfigSwVersion     	OBJECT-TYPE
    SYNTAX        				DisplayString(SIZE(0..255))
    MAX-ACCESS     				read-only
    STATUS          			current
    DESCRIPTION     			"This object identifies the Version Number of Current Release."
    ::= {ntronSystemConfig 2 }

ntronSystemConfigSwitchModel    OBJECT-TYPE
   	SYNTAX              		INTEGER
								{
									nt24k	(1),
									nt24kDR16 (2),
									nt24kDR24 (3),
									nt24k8Tx (4),
									nt24k8TxPoe (5),
									nt24k16Tx (6),
									nt24k16TxPoe (7),
									nt24k10Fx2 (8),
									nt24k10Fx2Poe (9),
									nt24k10Gx2 (10),
									nt24k10Gx2Poe (11),
									nt24k11Fx3 (12),
									nt24k11Fx3Poe (13),
									nt24k11Gx3 (14),
									nt24k11Gx3Poe (15),
									nt24k12Fx4 (16),
									nt24k12Fx4Poe (17),
									nt24k12Gx4 (18),
									nt24k12Gx4Poe (19),
									nt24k12SfpDm4 (20),
									nt24k12SfpDm4Poe (21),
									nt24k14Fx6 (22),
									nt24k14Fx6Poe (23),
									nt24k14Gx6 (24),
									nt24k14Gx6Poe (25),
									nt24k16M12 (26),
									nt24k16M12Poe (27),
									nt24k16M12R (28),
									nt24k16M12PoeR (29)
								}
   	MAX-ACCESS          		read-only
   	STATUS           		    current
   	DESCRIPTION					"This object will give the switch model."
    ::= {  ntronSystemConfig 3 }

ntronSystemConfigBuildDateAndTime 	OBJECT-TYPE
    SYNTAX              			DisplayString(SIZE(0..100))
    MAX-ACCESS          			read-only
    STATUS              			current
    DESCRIPTION 					"This object will hold the System Firmware build date and time."
    ::= { ntronSystemConfig 4 }

ntronSystemConfigTotalRam       OBJECT-TYPE
   	SYNTAX            			Integer32
   	MAX-ACCESS          		read-only
   	STATUS              		current
   	DESCRIPTION					"This object will give the total RAM available in the system."
    ::= {  ntronSystemConfig 5 }

ntronSystemConfigTotalFlash     OBJECT-TYPE
    SYNTAX             			Integer32
    MAX-ACCESS         			read-only
    STATUS             			current
    DESCRIPTION					"This object will give the total Flash available in system."
    ::= { ntronSystemConfig 6 }

ntronSystemConfigSwitchName     OBJECT-TYPE
    SYNTAX              		DisplayString(SIZE(0..255))
    MAX-ACCESS          		read-write
    STATUS              		current
    DESCRIPTION 				"This object is the name given to the switch."
    ::= {ntronSystemConfig 7}

ntronSystemConfigSwitchContact  OBJECT-TYPE
    SYNTAX              		DisplayString(SIZE(0..255))
    MAX-ACCESS          		read-write
    STATUS            			current
    DESCRIPTION     			"This object is contact information."
	::= {ntronSystemConfig 8 }

ntronSystemConfigSwitchLocation OBJECT-TYPE
   	SYNTAX              		DisplayString(SIZE(0..255))
   	MAX-ACCESS          		read-write
   	STATUS              		current
   	DESCRIPTION     			"This object is the switch location"
    ::= {ntronSystemConfig 9 }

ntronSystemConfigSysUpTime     	OBJECT-TYPE
    SYNTAX              		DisplayString(SIZE(0..255))
    MAX-ACCESS      			read-write
    STATUS         			    current
    DESCRIPTION    				"This object is how long the switch has been powered up."
    ::= {ntronSystemConfig 10 }

ntronSystemConfigValidPorts		OBJECT-TYPE
   	SYNTAX            			Integer32
   	MAX-ACCESS        			read-only
   	STATUS            			current
   	DESCRIPTION       			"This object will return the total number ports on the switch."
	::= { ntronSystemConfig 11 }

ntronSystemConfigInstalledPorts OBJECT-TYPE
	SYNTAX        				Integer32
    MAX-ACCESS         			read-only
    STATUS            			current
    DESCRIPTION					"This object will return the total number installed  ports on the switch."
	::= { ntronSystemConfig 12 }

ntronSystemConfigCurrentlyInstalledPorts 	OBJECT-TYPE
    SYNTAX             						Integer32
    MAX-ACCESS         						read-only
    STATUS        					     	current
    DESCRIPTION   							"This object will return the total number currently installed ports on the switch."
	::= { ntronSystemConfig 13 }

ntronSystemConfigMacAddress		OBJECT-TYPE
    SYNTAX             			DisplayString(SIZE(0..255))
    MAX-ACCESS         			read-only
    STATUS           			current
    DESCRIPTION    				"This object will return the MAC address of the switch."
    ::= { ntronSystemConfig 14 }

ntronSystemConfigCurrentIpAddress  	OBJECT-TYPE
   	SYNTAX             				IpAddress
   	MAX-ACCESS         				read-only
   	STATUS             				current
   	DESCRIPTION    					"The Current IP address is the one which is currently used."
	::= { ntronSystemConfig 15 }

ntronIpConfig    OBJECT IDENTIFIER ::= { ntronSystemConfig 16}

ntronIpConfigMode				OBJECT-TYPE
    SYNTAX  	   	    		INTEGER
								{
									static(1),
									dhcp(2)
								}
    MAX-ACCESS 					read-write
    STATUS          			current
    DESCRIPTION					"The IP Address can be obtained/configured by any of the above
								different ways."
	::= { ntronIpConfig 1 }

ntronIpConfigAddress 			OBJECT-TYPE
    SYNTAX             			IpAddress
    MAX-ACCESS          		read-write
    STATUS              		deprecated
    DESCRIPTION					"The Configured IP address of the device."
    ::= { ntronIpConfig 2 }

ntronIpConfigSubnet 			OBJECT-TYPE
   	SYNTAX       	    		IpAddress
   	MAX-ACCESS      			read-write
   	STATUS              		deprecated
   	DESCRIPTION         		"The Configured Subnet Mask of the device."
	::= { ntronIpConfig 3 }

ntronIpConfigGateway   			OBJECT-TYPE
   	SYNTAX     					IpAddress
   	MAX-ACCESS          		read-write
   	STATUS              		deprecated
   	DESCRIPTION         		"The Configured Gateway/Router address of the device."
	::= { ntronIpConfig 4 }

ntronIpConfigFallbackEnable 	OBJECT-TYPE
    SYNTAX       				INTEGER
								{
									disabled(1),
									enabled(2)
								}
	MAX-ACCESS 		         	read-write
    STATUS          	    	current
    DESCRIPTION 				"Fallback IP enabled/disabled."
	::= { ntronIpConfig 5 }

ntronIpConfigFallbackIPAddress 	OBJECT-TYPE
    SYNTAX              		IpAddress
    MAX-ACCESS         			read-write
    STATUS              		deprecated
    DESCRIPTION					"The Fallback IP address of the device."
	::= { ntronIpConfig 6 }

ntronIpConfigFallbackSubnet 	OBJECT-TYPE
    SYNTAX              		IpAddress
    MAX-ACCESS         		 	read-write
    STATUS              		deprecated
    DESCRIPTION					"The Fallback Subnet Mask of the device."
	::= { ntronIpConfig 7 }

ntronIpConfigFallbackGateway   	OBJECT-TYPE
    SYNTAX            			IpAddress
    MAX-ACCESS          		read-write
    STATUS              		deprecated
    DESCRIPTION					"The Fallback Gateway/Router address of the device."
	::= { ntronIpConfig 8 }

ntronClientId 		OBJECT IDENTIFIER ::= { ntronIpConfig 9}

ntronClientIdType				OBJECT-TYPE
   	SYNTAX   	  				INTEGER
								{
									switchName(1),
									macAddress(2),
									otherText(3),
									otherHex(4)
								}
	MAX-ACCESS     				read-write
    STATUS         				current
    DESCRIPTION    				"The Client Id type."
	::= { ntronClientId 1 }

ntronClientIdData				OBJECT-TYPE
    SYNTAX             			DisplayString(SIZE(0..255))
    MAX-ACCESS         			read-write
    STATUS             			current
    DESCRIPTION   				"This Client Id."
	::= { ntronClientId 2 }
ntronNetworkConfig		OBJECT IDENTIFIER ::= { ntronIpConfig 10}

ntronNetworkConfigCurrent	OBJECT IDENTIFIER	::= { ntronNetworkConfig 1}

ntronNetworkConfigCurrentIp				OBJECT-TYPE
	SYNTAX								IpAddress
	MAX-ACCESS							read-only
	STATUS								current
	DESCRIPTION							"The current IP Address of the device."
	::= { ntronNetworkConfigCurrent 1 }

ntronNetworkConfigCurrentSubnet			OBJECT-TYPE
	SYNTAX								IpAddress
	MAX-ACCESS							read-only
	STATUS								current
	DESCRIPTION							"The current Subnet mask of the device."
	::= { ntronNetworkConfigCurrent 2 }

ntronNetworkConfigCurrentGateway		OBJECT-TYPE
	SYNTAX								IpAddress
	MAX-ACCESS							read-only
	STATUS								current
	DESCRIPTION							"The current Gateway of the device."
	::= { ntronNetworkConfigCurrent 3 }

ntronNetworkConfigCurrentStaticIp		OBJECT-TYPE
	SYNTAX								IpAddress
	MAX-ACCESS							read-only
	STATUS								current
	DESCRIPTION							"The current static IP Address of the device."
	::= { ntronNetworkConfigCurrent 4 }

ntronNetworkConfigCurrentStaticSubnet	OBJECT-TYPE
	SYNTAX								IpAddress
	MAX-ACCESS							read-only
	STATUS								current
	DESCRIPTION							"The current static Subnet mask of the device."
	::= { ntronNetworkConfigCurrent 5 }

ntronNetworkConfigCurrentStaticGateway	OBJECT-TYPE
	SYNTAX								IpAddress
	MAX-ACCESS							read-only
	STATUS								current
	DESCRIPTION							"The current static Gateway of the device."
	::= { ntronNetworkConfigCurrent 6 }

ntronNetworkConfigCurrentFallbackIp		OBJECT-TYPE
	SYNTAX								IpAddress
	MAX-ACCESS							read-only
	STATUS								current
	DESCRIPTION							"The current fallback IP Address of the device."
	::= { ntronNetworkConfigCurrent 7 }

ntronNetworkConfigCurrentFallbackSubnet	OBJECT-TYPE
	SYNTAX								IpAddress
	MAX-ACCESS							read-only
	STATUS								current
	DESCRIPTION							"The current fallback Subnet mask of the device."
	::= { ntronNetworkConfigCurrent 8 }

ntronNetworkConfigCurrentFallbackGateway	OBJECT-TYPE
	SYNTAX								IpAddress
	MAX-ACCESS							read-only
	STATUS								current
	DESCRIPTION							"The current fallback Gateway of the device."
	::= { ntronNetworkConfigCurrent 9 }

ntronNetworkConfigStatic	OBJECT IDENTIFIER	::= { ntronNetworkConfig 2}

ntronNetworkConfigPendingStaticIp		OBJECT-TYPE
	SYNTAX								IpAddress
	MAX-ACCESS							read-write
	STATUS								current
	DESCRIPTION							"The static IP address of the device will be set when 'ntronNetworkConfigStaticUpdate'
										is set to 'action'."
	::= { ntronNetworkConfigStatic 1 }

ntronNetworkConfigPendingStaticSubnet	OBJECT-TYPE
	SYNTAX								IpAddress
	MAX-ACCESS							read-write
	STATUS								current
	DESCRIPTION							"The static subnet mask of the device will be set when 'ntronNetworkConfigStaticUpdate'
										is set to 'action'."
	::= { ntronNetworkConfigStatic 2 }

ntronNetworkConfigPendingStaticGateway	OBJECT-TYPE
	SYNTAX								IpAddress
	MAX-ACCESS							read-write
	STATUS								current
	DESCRIPTION							"The static gateway address of the device will be set when 'ntronNetworkConfigStaticUpdate'
										is set to 'action'."
	::= { ntronNetworkConfigStatic 3 }

ntronNetworkConfigStaticUpdate			OBJECT-TYPE
	SYNTAX								INTEGER
										{
											noAction	(1),
											action		(2)
										}
	MAX-ACCESS							read-write
	STATUS								current
	DESCRIPTION 						"Setting this object to 'action' will set the static IP (ntronNetworkConfigCurrentStaticIp),
										Subnet (ntronNetworkConfigCurrentStaticSubnet) and Gateway (ntronNetworkConfigCurrentStaticGateway)
										to the corresponding pending values (ntronNetworkConfigPendingStaticIp,
										ntronNetworkConfigPendingStaticSubnet, ntronNetworkConfigPendingStaticGateway). The value 'noAction'
										will be returned when the object is retrieved."
	::= { ntronNetworkConfigStatic 4 }

ntronNetworkConfigStaticErrorMsg		OBJECT-TYPE
	SYNTAX 								DisplayString(SIZE(0..255))
	MAX-ACCESS							read-only
	STATUS								current
	DESCRIPTION							"The error message, if any, after setting ntronNetworkConfigPendingStaticIp,
										ntronNetworkConfigPendingStaticSubnet, ntronNetworkConfigPendingStaticGateway, or
										ntronNetworkConfigStaticUpdate."
	::= { ntronNetworkConfigStatic 5 }

ntronNetworkConfigFallback	OBJECT IDENTIFIER	::= { ntronNetworkConfig 3}

ntronNetworkConfigPendingFallbackIp		OBJECT-TYPE
	SYNTAX								IpAddress
	MAX-ACCESS							read-write
	STATUS								current
	DESCRIPTION							"The fallback IP address of the device will be set when 'ntronNetworkConfigFallbackUpdate'
										is set to 'action'."
	::= { ntronNetworkConfigFallback 1 }

ntronNetworkConfigPendingFallbackSubnet	OBJECT-TYPE
	SYNTAX								IpAddress
	MAX-ACCESS							read-write
	STATUS								current
	DESCRIPTION							"The fallback subnet mask of the device will be set when 'ntronNetworkConfigFallbackUpdate'
										is set to 'action'."
	::= { ntronNetworkConfigFallback 2 }

ntronNetworkConfigPendingFallbackGateway	OBJECT-TYPE
	SYNTAX								IpAddress
	MAX-ACCESS							read-write
	STATUS								current
	DESCRIPTION							"The fallback gateway address of the device will be set when 'ntronNetworkConfigFallbackUpdate'
										is set to 'action'."
	::= { ntronNetworkConfigFallback 3 }

ntronNetworkConfigFallbackUpdate			OBJECT-TYPE
	SYNTAX								INTEGER
										{
											noAction	(1),
											action		(2)
										}
	MAX-ACCESS							read-write
	STATUS								current
	DESCRIPTION 						"Setting this object to 'action' will set the fallback IP (ntronNetworkConfigCurrentFallbackIp),
										Subnet (ntronNetworkConfigCurrentFallbackSubnet) and Gateway (ntronNetworkConfigCurrentFallbackGateway)
										to the corresponding pending values (ntronNetworkConfigPendingFallbackIp, ntronNetworkConfigPendingFallbackSubnet,
										ntronNetworkConfigPendingFallbackGateway). The value 'noAction' will be returned when the object is retrieved."
	::= { ntronNetworkConfigFallback 4 }

ntronNetworkConfigFallbackErrorMsg		OBJECT-TYPE
	SYNTAX 								DisplayString(SIZE(0..255))
	MAX-ACCESS							read-only
	STATUS								current
	DESCRIPTION							"The error message, if any, after setting ntronNetworkConfigPendingFallbackIp,
										ntronNetworkConfigPendingFallbackSubnet, ntronNetworkConfigPendingFallbackGateway, or
										ntronNetworkConfigFallbackUpdate."
	::= { ntronNetworkConfigFallback 5 }

ntronSystemConfigBrowser		OBJECT-TYPE
    SYNTAX       				INTEGER
								{
									disabled(1),
									enabled(2)
								}
	MAX-ACCESS 		         	read-write
    STATUS          	    	current
    DESCRIPTION 				"Browsing enabled/disabled."
    ::= { ntronSystemConfig 17 }

ntronSensor             OBJECT IDENTIFIER ::= { ntronSystemConfig 18}
ntronTemperature  		OBJECT IDENTIFIER ::= { ntronSensor 1}
ntronVoltage  			OBJECT IDENTIFIER ::= { ntronSensor 2}
ntronAmperage  			OBJECT IDENTIFIER ::= { ntronSensor 3}

ntronTemperatureDeviceTempTenthsC	OBJECT-TYPE
 	SYNTAX   	   			   		Integer32
    MAX-ACCESS        				read-only
    STATUS            				current
    DESCRIPTION    					"The device temperature in tenths of degrees Centigrade. E.g., 451 = 45.1 C"
	::= { ntronTemperature 1 }

ntronTemperatureDeviceTempTenthsF	OBJECT-TYPE
 	SYNTAX   	   			   		Integer32
    MAX-ACCESS        				read-only
    STATUS            				current
    DESCRIPTION    					"The device temperature in tenths of degrees Fahrenheit. E.g., 1016 = 101.6 F"
	::= { ntronTemperature 2 }

ntronTemperatureDeviceDisplay	OBJECT-TYPE
 	SYNTAX   	   			   	DisplayString(SIZE(0..255))
    MAX-ACCESS        			read-only
    STATUS            			current
    DESCRIPTION    				"Displays the device temperature in both Centigrade and Fahrenheit"
	::= { ntronTemperature 3 }

ntronTemperatureUpperThreshold	OBJECT-TYPE
 	SYNTAX   	   			   	Integer32(-60..120)
    MAX-ACCESS        			read-write
    STATUS            			current
    DESCRIPTION    				"The sensor upper threshold."
	::= { ntronTemperature 4 }

ntronTemperatureLowerThreshold	OBJECT-TYPE
	SYNTAX            			Integer32(-60..120)
	MAX-ACCESS         			read-write
	STATUS             			current
	DESCRIPTION	      		 	"The sensor lower threshold."
	::= { ntronTemperature 5 }

ntronVoltageDeviceVoltInputV1Tenths	OBJECT-TYPE
 	SYNTAX   	   			   		Integer32
    MAX-ACCESS        				read-only
    STATUS            				current
    DESCRIPTION    					"The device V1 voltage in tenths of volts. E.g., 251 = 25.1 V"
	::= { ntronVoltage 1 }

ntronVoltageDeviceVoltInputV2Tenths	OBJECT-TYPE
 	SYNTAX   	   			   		Integer32
    MAX-ACCESS        				read-only
    STATUS            				current
    DESCRIPTION    					"The device V2 voltage in tenths of volts. E.g., 251 = 25.1 V"
	::= { ntronVoltage 2 }

ntronAmperageDeviceAmpThousandths	OBJECT-TYPE
 	SYNTAX   	   			   		Integer32
    MAX-ACCESS        				read-only
    STATUS            				current
    DESCRIPTION    					"The device current in thousandths of amps. E.g., 325 = 0.325 A"
	::= { ntronAmperage 1 }

ntronAmperageDevicePowerTenths		OBJECT-TYPE
 	SYNTAX   	   			   		Integer32
    MAX-ACCESS        				read-only
    STATUS            				current
    DESCRIPTION    					"The device power in tenths of watts. E.g., 71 = 7.1 W"
	::= { ntronAmperage 2 }

ntronParam  OBJECT IDENTIFIER ::= { ntronSystemConfig 19}

ntronParamBmSfpDelayMs		OBJECT-TYPE
	SYNTAX            		Integer32
	MAX-ACCESS       		read-write
	STATUS            		current
	DESCRIPTION       		"The board Sfp Delay in Ms."
	::= { ntronParam 1 }

ntronSystemConfigSysRestore 	OBJECT-TYPE
	SYNTAX          			INTEGER
								{
									switchNoRestore (1),
									switchRestore   (2)
								}
	MAX-ACCESS 				  	read-write
	STATUS   				   	current
	DESCRIPTION 				"Setting this object to 'switchRestore' will cause the switch to
								load the saved configuration.  Setting
								this object to 'switchNoRestore' will have no effect.  The value
								'switchNoRestore' will be returned whenever this object is retrieved."
	::= { ntronSystemConfig 20 }

ntronSystemConfigSysSave    	OBJECT-TYPE
	SYNTAX						INTEGER
								{
									switchNoSave 	(1),
									switchSave		(2)
								}
	MAX-ACCESS					read-write
	STATUS						current
	DESCRIPTION					"Save all current changes to the switch's configuration for use after
								the next power cycle or reboot.  If a configuration device is installed,
								the configuration will also be saved to the device.  Only available when
								there is not a settings misconfiguration. The value 'switchNoSave' will be
								returned whenever this object is retrieved"
	::= { ntronSystemConfig 21}

ntronFileTransfer 	OBJECT IDENTIFIER ::= { ntronSystemConfig 22 }

ntronFileTransferProtocol		OBJECT-TYPE
	SYNTAX						INTEGER
								{
									tftp	(1)
								}
	MAX-ACCESS					read-write
	STATUS						current
	DESCRIPTION					"Protocol to be used for transfer"
	::= { ntronFileTransfer 1}

ntronFileTransferServer			OBJECT-TYPE
	SYNTAX						DisplayString(SIZE(0..255))
	MAX-ACCESS					read-write
	STATUS						current
	DESCRIPTION					"The IP address of the file server."
	::= { ntronFileTransfer 2}

ntronFileTransferFileName		OBJECT-TYPE
	SYNTAX						DisplayString(SIZE(0..255))
	MAX-ACCESS					read-write
	STATUS						current
	DESCRIPTION					"The name of the file to be imported or exported. The file name will be cleared
								only if the file transfer is successful, otherwise it will be left as is. The default
								file names for each action type are:
									upgradeSystemFirmware               : 'NT24k_image.tar'
									upgradeBootLoaderFirmware           : 'NT24k_bootloader.tar'
									importConfigurationToSwitch         : 'NT24k_settings.xml'
									exportSavedConfigurationFromSwitch  : 'NT24k_settings.xml'
									exportEventLogFromSwitch            : 'eventlog.csv'"
	::= { ntronFileTransfer 3}

ntronFileTransferActionType		OBJECT-TYPE
	SYNTAX						INTEGER
								{
									noAction                            (1),
									upgradeSystemFirmware               (2),
									upgradeBootLoaderFirmware           (3),
									importConfigurationToSwitch         (4),
									exportSavedConfigurationFromSwitch  (5),
									exportEventLogFromSwitch            (6)
								}
	MAX-ACCESS					read-write
	STATUS						current
	DESCRIPTION					"Setting this value to an acceptable value will initiate the requested action.
								The transfer types to be performed are:
									upgradeSystemFirmware               : Install system firmware to the switch.
									upgradeBootLoaderFirmware           : Install bootloader firmware to the switch.
									importConfigurationToSwitch         : Import  the switch configuration.
									exportSavedConfigurationFromSwitch  : Copy the saved configuration from the switch.
									exportEventLogFromSwitch            : Copy the event log from the switch.

                                    If downgrading to firmware version 2.1.10 or older please contact technical support for guidance."
	::= { ntronFileTransfer 4}

ntronFileTransferStatus			OBJECT-TYPE
	SYNTAX						INTEGER
								{
									noTransfer	(1),
									inProgress	(2),
									completed	(3),
									error		(4)
								}
	MAX-ACCESS					read-only
	STATUS						current
	DESCRIPTION					"The status of the current transfer."
	::= { ntronFileTransfer 5}

ntronFileTransferErrorMsg	OBJECT-TYPE
SYNTAX						DisplayString(SIZE(0..255))
MAX-ACCESS					read-only
STATUS						current
DESCRIPTION					"The error message, if any, for the current transfer."
	::= { ntronFileTransfer 6}

ntronFileTransferConfigKeepOptions	OBJECT IDENTIFIER ::= { ntronFileTransfer 10 }

ntronFileTransferConfigKeepOptionsClearAll	OBJECT-TYPE
	SYNTAX									INTEGER
											{
												noAction	(1),
												action 		(2)
											}
	MAX-ACCESS								read-write
	STATUS									current
	DESCRIPTION								"Sets ntronFileTransferConfigKeepOptionsKeepIp, ntronFileTransferConfigKeepOptionsKeepUser,
											ntronFileTransferConfigKeepOptionsKeepSnmp, ntronFileTransferConfigKeepOptionsKeepPoe, and
											ntronFileTransferConfigKeepOptionsKeepPortSecurity to 'no'. The value 'noAction' will be
											returned when this object is retrieved."
	::= { ntronFileTransferConfigKeepOptions 1 }

ntronFileTransferConfigKeepOptionsKeepAll	OBJECT-TYPE
	SYNTAX									INTEGER
											{
												noAction	(1),
												action 		(2)
											}
	MAX-ACCESS								read-write
	STATUS									current
	DESCRIPTION								"Sets ntronFileTransferConfigKeepOptionsKeepIp, ntronFileTransferConfigKeepOptionsKeepUser,
											ntronFileTransferConfigKeepOptionsKeepSnmp, ntronFileTransferConfigKeepOptionsKeepPoe, and
											ntronFileTransferConfigKeepOptionsKeepPortSecurity to 'yes'. The value 'noAction' will be
											returned when this object is retrieved."
	::= { ntronFileTransferConfigKeepOptions 2 }

ntronFileTransferConfigKeepOptionsKeepIp	OBJECT-TYPE
	SYNTAX									INTEGER
											{
												no 	(1),
												yes	(2)
											}
	MAX-ACCESS								read-write
	STATUS									current
	DESCRIPTION								"On a configuration import, the existing IP Address, Gateway, and Subnet Mask can be retained if
											this object is set to 'yes'."
	::= { ntronFileTransferConfigKeepOptions 3 }

ntronFileTransferConfigKeepOptionsKeepUser	OBJECT-TYPE
	SYNTAX									INTEGER
											{
												no 	(1),
												yes	(2)
											}
	MAX-ACCESS								read-write
	STATUS									current
	DESCRIPTION								"On a configuration import, the existing user names, passwords, and RADIUS configuration can be retained if this object is set
											to 'yes'."
	::= { ntronFileTransferConfigKeepOptions 4 }

ntronFileTransferConfigKeepOptionsKeepSNMP	OBJECT-TYPE
	SYNTAX									INTEGER
											{
												no 	(1),
												yes	(2)
											}
	MAX-ACCESS								read-write
	STATUS									current
    DESCRIPTION								"On a configuration import, the existing SNMP settings can be retained if this object is set to 'yes'."
	::= { ntronFileTransferConfigKeepOptions 5 }

	ntronFileTransferConfigKeepOptionsKeepPoe	OBJECT-TYPE
	SYNTAX										INTEGER
												{
													no 	(1),
													yes	(2)
												}
	MAX-ACCESS									read-write
	STATUS										current
	DESCRIPTION									"On a configuration import, the existing PoE Management settings can be retained if this object is set
												to 'yes', on a PoE capable device."
	::= { ntronFileTransferConfigKeepOptions 6 }

ntronFileTransferConfigKeepOptionsKeepPortSecurity	OBJECT-TYPE
	SYNTAX											INTEGER
													{
														no 	(1),
														yes	(2)
													}
	MAX-ACCESS										read-write
	STATUS											current
    DESCRIPTION										"On a configuration import, the existing Port Security settings can be retained if this object is set to 'yes'."
	::= { ntronFileTransferConfigKeepOptions 7 }

ntronSystemConfigBootloaderVersion	OBJECT-TYPE
	SYNTAX								DisplayString(SIZE(0..255))
	MAX-ACCESS							read-only
	STATUS								current
	DESCRIPTION							"Identifies the current bootloader version."
	::= { ntronSystemConfig 23}

ntronSystemFirmwareVersionUponReboot	OBJECT-TYPE
	SYNTAX								DisplayString(SIZE(0..255))
	MAX-ACCESS							read-only
	STATUS								current
	DESCRIPTION							"Identifies the firmware version after the next reboot of the switch."
	::= { ntronSystemConfig 24}

ntronSystemBootloaderVersionUponReboot	OBJECT-TYPE
	SYNTAX								DisplayString(SIZE(0..255))
	MAX-ACCESS							read-only
	STATUS								current
	DESCRIPTION							"Identifies the bootloader version after the next reboot of the switch."
	::= { ntronSystemConfig 25}

--  ----------------------------------------------------------------------------------
ntronSaveConfig     OBJECT IDENTIFIER  	::= {ntronSystemGroup 20}
--  ----------------------------------------------------------------------------------

ntronSaveConfigSave			OBJECT-TYPE
	SYNTAX					INTEGER
							{
								disabled (1),
								enabled (2)
							}
	MAX-ACCESS 				read-write
	STATUS 					deprecated
	DESCRIPTION				"If this configurable object is set to enabled then all the
							configured data of all the modules is written into flash."
::= { ntronSaveConfig 1}

ntronSaveConfigErase 		OBJECT-TYPE
							SYNTAX INTEGER
							{
								disable (1),
								enable (2),
								keepIp (3),
								keepUsers (4),
								keepIpAndUsers (5)
							}
	MAX-ACCESS 				read-write
	STATUS 					deprecated
	DESCRIPTION				"Setting this object to the value mentioned above will cause the specific
							function to be called. When performing the enable action either the config
							flags below or the same defaults as on the web will be used if not set as
							below. Any of the other options will ignore the below flags and do as they
							are described."
	::= { ntronSaveConfig 2}

ntronSaveConfigFlags 		OBJECT-TYPE
							SYNTAX INTEGER
							{
								none		(1),
								keepIp 		(2),
								keepUsers 	(3),
								keepSNMP 	(5),

								keepAll		(32),
								clear		(33)
							}
	MAX-ACCESS 				read-write
	STATUS 					deprecated
	DESCRIPTION				"If not manually set by the user the web default values will be used in the above
							action. Flags are reset to use the default values when ntronConfigErase is complete."
	::= { ntronSaveConfig 3}

--  ----------------------------------------------------------------------------------
ntronFactoryReset	OBJECT IDENTIFIER		::= {ntronSystemGroup 30}
--  ----------------------------------------------------------------------------------
ntronFactoryResetAction		OBJECT IDENTIFIER ::= { ntronFactoryReset 10 }

ntronFactoryResetActionReset			OBJECT-TYPE
	SYNTAX								INTEGER
										{
											noAction	(1),
											action		(2)
										}
	MAX-ACCESS							read-write
	STATUS								current
	DESCRIPTION							"Resets the switch's configuration to factory defaults except for
										any of the selected items in ntronFactoryResetOptions.  This only
										affects the current configuration.  A save must be performed to
										retain these changes after a power cycle or reboot.  The value
										'noAction' will be returned when this object is retrieved."
	::= { ntronFactoryResetAction 1 }

ntronFactoryResetActionClearAllOptions	OBJECT-TYPE
	SYNTAX								INTEGER
										{
											noAction	(1),
											action 		(2)
										}
	MAX-ACCESS							read-write
	STATUS								current
	DESCRIPTION							"Sets all the options in the ntronFactoryResetOptions group to 'no'.
										The value 'noAction' will be returned when this object is retrieved."
	::= { ntronFactoryResetAction 2 }

ntronFactoryResetActionKeepAllOptions	OBJECT-TYPE
	SYNTAX								INTEGER
										{
											noAction	(1),
											action 		(2)
										}
	MAX-ACCESS							read-write
	STATUS								current
	DESCRIPTION							"Sets all the options in the ntronFactoryResetOptions group to 'yes'.
										The value 'noAction' will be returned when this object is retrieved."
	::= { ntronFactoryResetAction 3 }

ntronFactoryResetOptions		OBJECT IDENTIFIER ::= { ntronFactoryReset 20 }

ntronFactoryResetOptionsKeepIp			OBJECT-TYPE
	SYNTAX								INTEGER
										{
											no	(1),
											yes	(2)
										}
	MAX-ACCESS							read-write
	STATUS								current
	DESCRIPTION							"Retain the existing IP address, subnet mask and gateway if desired."
	::= { ntronFactoryResetOptions 1 }

ntronFactoryResetOptionsKeepUser		OBJECT-TYPE
	SYNTAX								INTEGER
										{
											no	(1),
											yes	(2)
										}
	MAX-ACCESS							read-write
	STATUS								current
	DESCRIPTION							"Retain the existing user names, passwords. and RADIUS configuration if desired."
	::= { ntronFactoryResetOptions 2 }

ntronFactoryResetOptionsKeepSNMP		OBJECT-TYPE
	SYNTAX								INTEGER
										{
											no	(1),
											yes	(2)
										}
	MAX-ACCESS							read-write
	STATUS								current
    DESCRIPTION							"Retain the existing SNMP settings if desired."
	::= { ntronFactoryResetOptions 3 }

ntronFactoryResetOptionsKeepPoe			OBJECT-TYPE
	SYNTAX								INTEGER
										{
											no	(1),
											yes	(2)
										}
	MAX-ACCESS							read-write
	STATUS								current
	DESCRIPTION							"Retain the existing PoE Management settings if desired, on a PoE capable device."
	::= { ntronFactoryResetOptions 4 }

ntronFactoryResetOptionsKeepPortSecurity OBJECT-TYPE
	SYNTAX								INTEGER
										{
											no	(1),
											yes	(2)
										}
	MAX-ACCESS							read-write
	STATUS								current
	DESCRIPTION							"Retain the existing Port Security settings if desired."
	::= { ntronFactoryResetOptions 5 }

--  ----------------------------------------------------------------------------------
--
--	FaultGroup
--
--  ----------------------------------------------------------------------------------

--  ----------------------------------------------------------------------------------
ntronFaultConfig     	 OBJECT IDENTIFIER  	::= {ntronFaultGroup 10}
--  ----------------------------------------------------------------------------------

ntronFaultConfigContactAction		OBJECT-TYPE
	SYNTAX     				  		INTEGER
									{
										closeOnFault(1),
										openOnFault(2)
									}
	MAX-ACCESS         			 	read-write
    STATUS              			current
    DESCRIPTION 					"Indicate fault by opening or closing contact."
	 ::= { ntronFaultConfig 1 }

ntronFaultConfigFaultsTable     		OBJECT-TYPE
   	SYNTAX    	         		SEQUENCE OF NtronConfigFaults
	MAX-ACCESS  	        	not-accessible
   	STATUS          	       	current
   	DESCRIPTION  				"The  fault config table."
	::= { ntronFaultConfig 2 }

ntronConfigFaultsFault  	  	OBJECT-TYPE
    SYNTAX                		NtronConfigFaults
    MAX-ACCESS            		not-accessible
    STATUS                		current
    DESCRIPTION					"An entry in the ntronFaultTable."
	INDEX      					{ ntronConfigFaultsFaultId }
    ::= { ntronFaultConfigFaultsTable 1 }

NtronConfigFaults ::= SEQUENCE {
    ntronConfigFaultsFaultName		DisplayString,
	ntronConfigFaultsFaultWeb		INTEGER,
	ntronConfigFaultsFaultLED		INTEGER,
	ntronConfigFaultsFaultContact	INTEGER,
    ntronConfigFaultsFaultId        Integer32
    }

ntronConfigFaultsFaultName      OBJECT-TYPE
    SYNTAX     			        DisplayString(SIZE(0..255))
    MAX-ACCESS         			read-only
    STATUS              		current
    DESCRIPTION 				"The fault name."
    ::= {ntronConfigFaultsFault 1}

ntronConfigFaultsFaultWeb       OBJECT-TYPE
   	SYNTAX 		              	INTEGER
								{
                            		disabled (1),
                            		enabled  (2)
                                }
   	MAX-ACCESS  	          	read-write
   	STATUS          	      	current
   	DESCRIPTION					"Display the fault on the web page."
	::= { ntronConfigFaultsFault 2}

ntronConfigFaultsFaultLED     	OBJECT-TYPE
   	SYNTAX      	         	INTEGER
								{
                            		disabled (1),
                            		enabled  (2)
                                }
   	MAX-ACCESS	            	read-write
   	STATUS      	          	current
   	DESCRIPTION			      	"Display the fault on the power LED."
	::= { ntronConfigFaultsFault 3}

ntronConfigFaultsFaultContact  	OBJECT-TYPE
   	SYNTAX               		INTEGER
								{
                            		disabled (1),
                            		enabled  (2)
                                }
   	MAX-ACCESS            		read-write
   	STATUS                		current
   	DESCRIPTION				 	"Perform the relay action when a fault occurs."
    ::= { ntronConfigFaultsFault 4}

ntronConfigFaultsFaultId		OBJECT-TYPE
   	SYNTAX              	  	Integer32
   	MAX-ACCESS            		read-only
   	STATUS                		current
   	DESCRIPTION					"The fault Id."
   	::= { ntronConfigFaultsFault 5}

ntronFaultConfigFaultEventsTable    OBJECT-TYPE
    SYNTAX                          SEQUENCE OF NtronConfigFaultEvents
    MAX-ACCESS                      not-accessible
    STATUS                          current
    DESCRIPTION                     "The fault event config table."
    ::= { ntronFaultConfig 3 }

ntronConfigFaultEventsFaultEvent    OBJECT-TYPE
    SYNTAX                          NtronConfigFaultEvents
    MAX-ACCESS                      not-accessible
    STATUS                          current
    DESCRIPTION                     "An entry in the ntronFaultEventsTable."
    INDEX                           { ntronConfigFaultsFaultEventId }
    ::= { ntronFaultConfigFaultEventsTable 1 }

NtronConfigFaultEvents ::= SEQUENCE {
    ntronConfigFaultsFaultEventsName        DisplayString,
    ntronConfigFaultsFaultEventSendEvent    INTEGER,
    ntronConfigFaultsFaultEventSeverity     INTEGER,
    ntronConfigFaultsFaultEventId           Integer32
    }

ntronConfigFaultsFaultEventsName    OBJECT-TYPE
    SYNTAX                          DisplayString(SIZE(0..255))
    MAX-ACCESS                      read-only
    STATUS                          current
    DESCRIPTION                     "The fault name."
    ::= {ntronConfigFaultEventsFaultEvent 1}

ntronConfigFaultsFaultEventSendEvent        OBJECT-TYPE
    SYNTAX                                  INTEGER
                                            {
                                                disabled      (1),
                                                enabled       (2)
                                            }
    MAX-ACCESS                              read-write
    STATUS                                  current
    DESCRIPTION                             "The fault is sent to the configured log(s). See the Event Log and
                                            Syslog configuration."
    ::= { ntronConfigFaultEventsFaultEvent 2 }

ntronConfigFaultsFaultEventSeverity         OBJECT-TYPE
    SYNTAX                                  INTEGER
                                            {
                                                emergency0      (1),
                                                alert1          (2),
                                                critical2       (3),
                                                error3          (4),
                                                warning4        (5),
                                                notice5         (6),
                                                informational6  (7),
                                                debug7          (8)
                                            }
    MAX-ACCESS                              read-write
    STATUS                                  current
    DESCRIPTION                             "The fault will generate an event at this severity level."
    ::= { ntronConfigFaultEventsFaultEvent 3 }

ntronConfigFaultsFaultEventId               OBJECT-TYPE
    SYNTAX                                  Integer32
    MAX-ACCESS                              read-only
    STATUS                                  current
    DESCRIPTION                             "The fault Id."
    ::= { ntronConfigFaultEventsFaultEvent 4 }

--  ----------------------------------------------------------------------------------
ntronFaultStatus  	 OBJECT IDENTIFIER  	::= {ntronFaultGroup 20}
--  ----------------------------------------------------------------------------------

ntronFaultListContactStatus		OBJECT-TYPE
	SYNTAX       				INTEGER
								{
									open(1),
									closed(2)
								}
	MAX-ACCESS          		read-only
    STATUS              		current
    DESCRIPTION 				"Current relay status."
	 ::= { ntronFaultStatus 1 }

ntronValidFaultsTable     		OBJECT-TYPE
   	SYNTAX     		        	SEQUENCE OF NtronValidFaults
	MAX-ACCESS      		   	not-accessible
   	STATUS                 		current
   	DESCRIPTION   				"The valid fault list table."
    ::= { ntronFaultStatus 2 }

ntronValidFaultsFault    		OBJECT-TYPE
   	SYNTAX                		NtronValidFaults
   	MAX-ACCESS            		not-accessible
   	STATUS                		current
   	DESCRIPTION					"An entry in the ntronValidFaultsTable."
	INDEX      					{ ntronValidFaultsFaultId }
    ::= { ntronValidFaultsTable 1 }

NtronValidFaults ::= SEQUENCE {
    ntronValidFaultsFaultName			DisplayString,
	ntronValidFaultsFaultStatus			INTEGER,
	ntronValidFaultsFaultDestription	DisplayString,
    ntronValidFaultsFaultId  			Integer32
    }

ntronValidFaultsFaultName       OBJECT-TYPE
    SYNTAX             			DisplayString(SIZE(0..255))
    MAX-ACCESS          		read-only
    STATUS              		current
    DESCRIPTION 				"Name of the fault."
    ::= {ntronValidFaultsFault 1}

ntronValidFaultsFaultStatus     OBJECT-TYPE
    SYNTAX 	    		        INTEGER
								{
									noFault (1),
									fault  (2)
                                }
   	MAX-ACCESS            		read-only
   	STATUS             			current
   	DESCRIPTION					"Current status of the fault."
	::= { ntronValidFaultsFault 2}

ntronValidFaultsFaultDestription 	OBJECT-TYPE
   SYNTAX              				DisplayString(SIZE(0..255))
   MAX-ACCESS          				read-only
   STATUS              				current
   DESCRIPTION 						"Fault description."
   ::= { ntronValidFaultsFault 3}

ntronValidFaultsFaultId			OBJECT-TYPE
   	SYNTAX        				Integer32
   	MAX-ACCESS        			read-only
   	STATUS              		current
   	DESCRIPTION					"Fault Id number."
   	::= { ntronValidFaultsFault 4}

--  ----------------------------------------------------------------------------------
--
--	IgmpGroup
--
--  ----------------------------------------------------------------------------------

--  ----------------------------------------------------------------------------------
ntronIgmpConfig   OBJECT IDENTIFIER  	::= {ntronIgmpGroup 10}
--  ----------------------------------------------------------------------------------

ntronIgmpConfigStatus			OBJECT-TYPE
    SYNTAX						INTEGER
								{
									disabled (1),
									enabled (2)
								}
	MAX-ACCESS					read-write
	STATUS						current
    DESCRIPTION					"This object holds the current state of the igmp. By configuring this to
								enabled, the igmp will be enabled."
	::= {ntronIgmpConfig 1 }

ntronIgmpConfigQueryMode  		OBJECT-TYPE
    SYNTAX						INTEGER
								{
									auto (3),
									on 	(2),
									off (1)
								}
    MAX-ACCESS					read-write
    STATUS						current
    DESCRIPTION					"To set the switch's query mode."
	::= {ntronIgmpConfig 2}

ntronIgmpConfigRouterMode    	OBJECT-TYPE
    SYNTAX						INTEGER
								{
									auto (3),
									manual (2),
									none (1)
								}
	MAX-ACCESS					read-write
	STATUS						current
    DESCRIPTION					"To set the switch's router mode."
	::= {ntronIgmpConfig 3}

ntronIgmpConfigRemoveUnusedGroups	OBJECT-TYPE
	SYNTAX							INTEGER
									{
										disabled (1),
										enabled (2)
									}
	MAX-ACCESS						read-write
	STATUS							current
    DESCRIPTION						"By configuring this to	disabled, the unused groups will not be removed."
	::= {ntronIgmpConfig 4 }

ntronIgmpConfigManualRouterPorts   	OBJECT-TYPE
    SYNTAX             			 	DisplayString(SIZE(0..255))
    MAX-ACCESS          			read-write
    STATUS              			current
    DESCRIPTION 					"String containing list of the manuual router ports."
    ::= {ntronIgmpConfig 5}

ntronIgmpConfigRFilterPorts   	OBJECT-TYPE
    SYNTAX             			DisplayString(SIZE(0..255))
    MAX-ACCESS          		read-write
    STATUS              		current
    DESCRIPTION 				"String containing list of the RFilter ports."
    ::= {ntronIgmpConfig 6}

--  ----------------------------------------------------------------------------------
ntronIgmpStatus   OBJECT IDENTIFIER  	::= {ntronIgmpGroup 20}
--  ----------------------------------------------------------------------------------

ntronIgmpListNumberOfGroups     OBJECT-TYPE
   	SYNTAX            			Integer32
   	MAX-ACCESS          		read-only
   	STATUS              		current
   	DESCRIPTION					"This object will give the current number of IGMP groups."
    ::= {  ntronIgmpStatus 1 }

ntronIgmpGroupsTable     		OBJECT-TYPE
   	SYNTAX     		        	SEQUENCE OF NtronIgmpGroups
	MAX-ACCESS      		   	not-accessible
   	STATUS                 		current
   	DESCRIPTION   				"The igmp groups table."
    ::= { ntronIgmpStatus 2 }

ntronIgmpGroupsGroup    		OBJECT-TYPE
   	SYNTAX                		NtronIgmpGroups
   	MAX-ACCESS            		not-accessible
   	STATUS                		current
   	DESCRIPTION					"An entry in the ntronIgmpGroupsTable."
	INDEX      					{ ntronIgmpGroupsGroupId }
    ::= { ntronIgmpGroupsTable 1 }

NtronIgmpGroups  ::= SEQUENCE {
	ntronIgmpGroupsGroupIp			IpAddress,
	ntronIgmpGroupsGroupPortName	DisplayString,
	ntronIgmpGroupsGroupVlanId		Integer32,
    ntronIgmpGroupsGroupId  		Integer32
    }

ntronIgmpGroupsGroupIp			OBJECT-TYPE
   	SYNTAX						IpAddress
   	MAX-ACCESS					read-only
   	STATUS						current
   	DESCRIPTION					"The IpAddress of the Multicast Group."
   	::= { ntronIgmpGroupsGroup 1 }

ntronIgmpGroupsGroupPortName	OBJECT-TYPE
	SYNTAX             			DisplayString(SIZE(0..255))
   	MAX-ACCESS					read-only
   	STATUS						current
   	DESCRIPTION					"The port name from which the multicast Ip is received."
   	::= { ntronIgmpGroupsGroup 2}

ntronIgmpGroupsGroupVlanId		OBJECT-TYPE
   	SYNTAX						Integer32
   	MAX-ACCESS					read-only
   	STATUS						current
   	DESCRIPTION					"The Vlan Id to which the group port belongs."
   	::= { ntronIgmpGroupsGroup 3 }

ntronIgmpGroupsGroupId			OBJECT-TYPE
   	SYNTAX						Integer32
   	MAX-ACCESS					read-only
   	STATUS						current
   	DESCRIPTION					"The unique identifier to identify the igmp member."
   	::= { ntronIgmpGroupsGroup 4 }

ntronIgmpRoutersTable     		OBJECT-TYPE
   	SYNTAX     		        	SEQUENCE OF NtronIgmpRouters
	MAX-ACCESS      		   	not-accessible
   	STATUS                 		current
   	DESCRIPTION   				"The igmp routers table."
    ::= { ntronIgmpStatus 3 }

ntronIgmpRoutersRouter    		OBJECT-TYPE
   	SYNTAX                		NtronIgmpRouters
   	MAX-ACCESS            		not-accessible
   	STATUS                		current
   	DESCRIPTION					"An entry in the ntronIgmpRoutersTable."
	INDEX      					{ ntronIgmpGroupsGroupId }
    ::= { ntronIgmpRoutersTable 1 }

NtronIgmpRouters  ::= SEQUENCE {
	ntronIgmpRoutersRouterIp		IpAddress,
	ntronIgmpRoutersRouterPortName	DisplayString,
	ntronIgmpRoutersRouterVlanId	Integer32,
    ntronIgmpRoutersRouterId  		Integer32
    }

ntronIgmpRoutersRouterIp		OBJECT-TYPE
   	SYNTAX						IpAddress
   	MAX-ACCESS					read-only
   	STATUS						current
   	DESCRIPTION					"The IpAddress of the Multicast Group."
   	::= { ntronIgmpRoutersRouter 1 }

ntronIgmpRoutersRouterPortName	OBJECT-TYPE
   SYNTAX             			DisplayString(SIZE(0..255))
   	MAX-ACCESS					read-only
   	STATUS						current
   	DESCRIPTION					"The port name from which the multicast Ip is received."
   	::= { ntronIgmpRoutersRouter 2}

ntronIgmpRoutersRouterVlanId	OBJECT-TYPE
   	SYNTAX						Integer32
   	MAX-ACCESS					read-only
   	STATUS						current
   	DESCRIPTION					"The Vlan Id to which the router port belongs."
   	::= { ntronIgmpRoutersRouter 3 }

ntronIgmpRoutersRouterId		OBJECT-TYPE
   	SYNTAX						Integer32
   	MAX-ACCESS					read-only
   	STATUS						current
   	DESCRIPTION					"The unique identifier to identify the router member."
   	::= { ntronIgmpRoutersRouter 4 }

ntronIgmpNringRouterPorts   	OBJECT-TYPE
    SYNTAX             			DisplayString(SIZE(0..255))
    MAX-ACCESS          		read-only
    STATUS              		current
    DESCRIPTION 				"String containing list of the N-Ring router ports."
    ::= { ntronIgmpStatus 4 }

ntronIgmpNlinkRouterPorts   	OBJECT-TYPE
    SYNTAX             			DisplayString(SIZE(0..255))
    MAX-ACCESS          		read-only
    STATUS              		current
    DESCRIPTION 				"String containing list of the N-Link router ports."
    ::= { ntronIgmpStatus 5 }

ntronIgmpActiveQuerierIp		OBJECT-TYPE
	SYNTAX						IpAddress
	MAX-ACCESS					read-only
	STATUS						current
	DESCRIPTION					"The IpAddress of the Active Querier."
    ::= { ntronIgmpStatus 6 }

--  ----------------------------------------------------------------------------------
--
--	NringGroup
--
--  ----------------------------------------------------------------------------------

--  ----------------------------------------------------------------------------------
ntronNringConfig   OBJECT IDENTIFIER  	::= {ntronNringGroup 10}
--  ----------------------------------------------------------------------------------

ntronNringConfigMode    	OBJECT-TYPE
    SYNTAX						INTEGER
								{
									 disabled(1),
									 autoMember(2),
									 manager(3),
									 multiMember(4)
								}
	MAX-ACCESS					read-write
	STATUS						current
    DESCRIPTION					"Operational mode of N-Ring system."
	::= {ntronNringConfig 1}

ntronNringConfigVlanId	OBJECT-TYPE
   	SYNTAX						Integer32
   	MAX-ACCESS					read-write
   	STATUS						current
   	DESCRIPTION					"The Vlan Id which N-Ring ports are assigned."
   	::= { ntronNringConfig 2 }

ntronNringConfigVlanTagged    	OBJECT-TYPE
    SYNTAX						INTEGER
								{
									 untagged(1),
									 tagged(2)
								}
	MAX-ACCESS					read-write
	STATUS						current
    DESCRIPTION					"Selection as to whether the N-Ring ports are
								members of the VLAN's Tagged or Untagged ports."
	::= {ntronNringConfig 3}

ntronNringConfigRingNo	OBJECT-TYPE
   	SYNTAX						Integer32
   	MAX-ACCESS					read-write
   	STATUS						current
   	DESCRIPTION					"N-Ring Id number."
   	::= { ntronNringConfig 4 }

ntronNringConfigHealthMs	OBJECT-TYPE
   	SYNTAX						Integer32
   	MAX-ACCESS					read-write
   	STATUS						current
   	DESCRIPTION					"The amount of time to wait in milliseconds before sending
								Self-Health packet."
   	::= { ntronNringConfig 5 }

ntronNringConfigMaxMissed	OBJECT-TYPE
   	SYNTAX						Integer32
   	MAX-ACCESS					read-write
   	STATUS						current
   	DESCRIPTION					"The number of consecutive missed Self-Health packets that
								constitute a fault."
   	::= { ntronNringConfig 6 }

ntronNringConfigHysteresisMs	OBJECT-TYPE
   	SYNTAX						Integer32
   	MAX-ACCESS					read-write
   	STATUS						current
   	DESCRIPTION					"Delay Before Re-entering Broken State (msecs)."
   	::= { ntronNringConfig 7 }

ntronNringConfigSignOnDelayHealthyMs	OBJECT-TYPE
   	SYNTAX						Integer32
   	MAX-ACCESS					read-write
   	STATUS						current
   	DESCRIPTION					"The amount of time to wait in milliseconds before requesting
								initial sign-on information from N-Ring members."
   	::= { ntronNringConfig 8 }

ntronNringConfigSignOnIntervalHealthyMs	OBJECT-TYPE
   	SYNTAX						Integer32
   	MAX-ACCESS					read-write
   	STATUS						current
   	DESCRIPTION					"The interval of time to wait in milliseconds before requesting
								subsequent sign-on information from N-Ring members when the N-Ring
								is broken."
   	::= { ntronNringConfig 9 }

ntronNringConfigSignOnDelayBrokenMs	OBJECT-TYPE
   	SYNTAX						Integer32
   	MAX-ACCESS					read-write
   	STATUS						current
   	DESCRIPTION					"How long to wait before requesting sign on information (when broken)."
   	::= { ntronNringConfig 10 }

ntronNringConfigSignOnIntervalBrokenMs	OBJECT-TYPE
   	SYNTAX						Integer32
   	MAX-ACCESS					read-write
   	STATUS						current
   	DESCRIPTION					"The amount of time, in milliseconds, that must elapse before the
								ring is allowed to go back into the broken state."
   	::= { ntronNringConfig 11 }

ntronNringConfigSignOnMatch	OBJECT-TYPE
   	SYNTAX						Integer32
   	MAX-ACCESS					read-write
   	STATUS						current
   	DESCRIPTION					"The number of times the switch count must match before starting
								 the sign-on process."
   	::= { ntronNringConfig 12 }

ntronNringConfigSignOnInfoDelayMs OBJECT-TYPE
   	SYNTAX						Integer32
   	MAX-ACCESS					read-write
   	STATUS						current
   	DESCRIPTION					"Sign-On Info Spacing Multiplier (msecs)."
   	::= { ntronNringConfig 13 }

ntronNringConfigSignOnInfoRetryMs	OBJECT-TYPE
   	SYNTAX						Integer32
   	MAX-ACCESS					read-write
   	STATUS						current
   	DESCRIPTION					"The amount of time the ring member will wait in milliseconds
								for the ring manager to acknowledge receipt of the member's
								information before the member tries to re-send the information."
   	::= { ntronNringConfig 14 }

ntronNringConfigKeepAliveSeconds	OBJECT-TYPE
   	SYNTAX						Integer32
   	MAX-ACCESS					read-write
   	STATUS						current
   	DESCRIPTION					"The amount of time to wait in seconds to receive
								a keep-alive request before switching from active
								member back to auto member."
   	::= { ntronNringConfig 15 }

ntronNringConfigAutoMemberDetectionSeconds	OBJECT-TYPE
   	SYNTAX						Integer32(2..180)
   	MAX-ACCESS					read-write
   	STATUS						current
   	DESCRIPTION					"The amount of time to wait in seconds
								to receive N-Ring frames on any auto member port (at boot up)
								before assuming the switch is not part of an N-Ring."
   	::= { ntronNringConfig 16 }

ntronNringConfigStatusRefreshRate	OBJECT-TYPE
   	SYNTAX						Integer32
   	MAX-ACCESS					read-write
   	STATUS						current
   	DESCRIPTION					"How often the N-Ring Status View web page is refreshed in seconds."
   	::= { ntronNringConfig 17 }

ntronNringConfigSelectedPortSet	OBJECT-TYPE
   	SYNTAX						Integer32
   	MAX-ACCESS					read-write
   	STATUS						current
   	DESCRIPTION					"The current N-Ring port set."
   	::= { ntronNringConfig 18 }

ntronNringPortSetsTable     		OBJECT-TYPE
   	SYNTAX    	         		SEQUENCE OF NtronNringPortSets
	MAX-ACCESS  	        	not-accessible
   	STATUS          	       	current
   	DESCRIPTION  				"N-Ring Port Sets table."
	::= { ntronNringConfig 19 }

ntronNringPortSetsPortSet  	  	OBJECT-TYPE
    SYNTAX                		NtronNringPortSets
    MAX-ACCESS            		not-accessible
    STATUS                		current
    DESCRIPTION					"An entry in the ntronFaultTable."
	INDEX      					{ ntronConfigFaultsFaultId }
    ::= { ntronNringPortSetsTable 1 }

NtronNringPortSets ::= SEQUENCE {
    ntronNringPortSetsPortSetId 	 	Integer32,
	ntronNringPortSetsPortSetPortx	DisplayString,
	ntronNringPortSetsPortSetPorty	DisplayString
    }

ntronNringPortSetsPortSetId		OBJECT-TYPE
   	SYNTAX						Integer32
   	MAX-ACCESS					read-write
   	STATUS						current
   	DESCRIPTION					"Id of the N-Ring port set."
   	::= { ntronNringPortSetsPortSet 1 }

ntronNringPortSetsPortSetPortx	OBJECT-TYPE
   SYNTAX             			DisplayString(SIZE(0..255))
   	MAX-ACCESS					read-only
   	STATUS						current
   	DESCRIPTION					"Port 1 of the N-Ring port set."
   	::= { ntronNringPortSetsPortSet 2}

ntronNringPortSetsPortSetPorty	OBJECT-TYPE
   SYNTAX             			DisplayString(SIZE(0..255))
   	MAX-ACCESS					read-only
   	STATUS						current
   	DESCRIPTION					"Port 2 of the N-Ring port set."
   	::= { ntronNringPortSetsPortSet 3}

ntronNringMembershipsTable     	OBJECT-TYPE
   	SYNTAX    	         		SEQUENCE OF NtronNringMemberships
	MAX-ACCESS  	        	not-accessible
   	STATUS          	       	current
   	DESCRIPTION  				"N-Ring Memberships table."
	::= { ntronNringConfig 20 }

ntronNringMembershipsMembership OBJECT-TYPE
    SYNTAX                		NtronNringMemberships
    MAX-ACCESS            		not-accessible
    STATUS                		current
    DESCRIPTION					"An entry in the ntronFaultTable."
	INDEX      					{ ntronConfigFaultsFaultId }
    ::= { ntronNringMembershipsTable 1 }

NtronNringMemberships ::= SEQUENCE {
    ntronNringMembershipsMembershipRingNo 	 	Integer32,
	ntronNringMembershipsMembershipPortSetId	Integer32,
	ntronNringMembershipsMembershipVlanId		Integer32,
	ntronNringMembershipsMembershipVlanTagged	INTEGER
    }

ntronNringMembershipsMembershipRingNo	OBJECT-TYPE
   	SYNTAX								Integer32(1..17)
   	MAX-ACCESS							read-only
   	STATUS								current
   	DESCRIPTION							"Ring number of the N-Ring membership."
   	::= { ntronNringMembershipsMembership 1 }

ntronNringMembershipsMembershipPortSetId	OBJECT-TYPE
	SYNTAX             					Integer32(1..31)
   	MAX-ACCESS							read-write
   	STATUS								current
   	DESCRIPTION							"Port set Id of the N-Ring membership."
   	::= { ntronNringMembershipsMembership 2 }

ntronNringMembershipsMembershipVlanId	OBJECT-TYPE
   	SYNTAX								Integer32(1..4094)
   	MAX-ACCESS							read-write
   	STATUS								current
   	DESCRIPTION							"VLAN Id of the N-Ring membership."
   	::= { ntronNringMembershipsMembership 3 }

ntronNringMembershipsMembershipVlanTagged	OBJECT-TYPE
    SYNTAX								INTEGER
										{
											untagged(1),
											tagged(2)
										}
   	MAX-ACCESS							read-write
   	STATUS								current
   	DESCRIPTION							"VLAN tagging of the N-Ring membership."
   	::= { ntronNringMembershipsMembership 4 }

--  ----------------------------------------------------------------------------------
ntronNringStatus   OBJECT IDENTIFIER  	::= {ntronNringGroup 20}
--  ----------------------------------------------------------------------------------

ntronNringStatusState    	OBJECT-TYPE
    SYNTAX						INTEGER
								{
									 disabled(1),
									 autoMember(2),
									 activeMember(3),
									 manager(4),
									 multiMember(5),
									 unknown(6)
								}
	MAX-ACCESS					read-only
	STATUS						current
    DESCRIPTION					"Current N-Ring status."
	::= {ntronNringStatus 1}

ntronNringStatusVersion		OBJECT-TYPE
   	SYNTAX						Integer32
   	MAX-ACCESS					read-only
   	STATUS						current
   	DESCRIPTION					"Current N-Ring version."
   	::= { ntronNringStatus 2 }

ntronNringStatusBrokenPorts    	OBJECT-TYPE
    SYNTAX						INTEGER
								{
									 noFault(1),
									 lowPortBroken(2),
									 highPortBroken(3),
									 bothPortsBroken(4)
								}
	MAX-ACCESS					read-only
	STATUS						current
    DESCRIPTION					"Current N-Ring fault."
	::= {ntronNringStatus 3}

--  ----------------------------------------------------------------------------------
--
--	NViewGroup
--
--  ----------------------------------------------------------------------------------

--  ----------------------------------------------------------------------------------
ntronNViewConfig   OBJECT IDENTIFIER  	::= {ntronNViewGroup 10}
--  ----------------------------------------------------------------------------------

ntronNViewConfigStatus      OBJECT-TYPE
    SYNTAX               	INTEGER
							{
                            	disabled (1),
                            	enabled  (2)
                            }
	MAX-ACCESS          	read-write
	STATUS              	current
	DESCRIPTION 			"Global status of NView broadcasts."
    ::= { ntronNViewConfig 1 }

ntronNViewConfigInterval    OBJECT-TYPE
    SYNTAX 	            	Integer32(5..500)
	MAX-ACCESS          	read-write
	STATUS              	current
	DESCRIPTION 			"Global interval between NView broadcasts."
	::= { ntronNViewConfig 2 }

ntronNViewConfigSendAutocastPorts	OBJECT-TYPE
	SYNTAX             				DisplayString(SIZE(0..255))
   	MAX-ACCESS						read-write
   	STATUS							current
   	DESCRIPTION						"Ports to send NView autocast packets on."
   	::= { ntronNViewConfig 3}

ntronNViewConfigSendMibStatsPorts	OBJECT-TYPE
	SYNTAX             				DisplayString(SIZE(0..255))
   	MAX-ACCESS						read-write
   	STATUS							current
   	DESCRIPTION						"Ports to send MIB counters inside autocast packets."
   	::= { ntronNViewConfig 4}

--  ----------------------------------------------------------------------------------
--
--	PortGroup
--
--  ----------------------------------------------------------------------------------

--  ----------------------------------------------------------------------------------
ntronPortConfig   OBJECT IDENTIFIER  	::= {ntronPortGroup 10}
--  ----------------------------------------------------------------------------------

ntronPortsTable     		OBJECT-TYPE
   	SYNTAX    	         		SEQUENCE OF NtronPorts
	MAX-ACCESS  	        	not-accessible
   	STATUS          	       	current
   	DESCRIPTION  				""
	::= { ntronPortConfig 1 }

ntronPortsPort  	  	OBJECT-TYPE
    SYNTAX                		NtronPorts
    MAX-ACCESS            		not-accessible
    STATUS                		current
    DESCRIPTION					"An entry in the ntronPortsTable."
	INDEX      					{ntronPortsPortPortNumberId }
    ::= { ntronPortsTable 1 }

NtronPorts ::= SEQUENCE {
    ntronPortsPortPortNumber            DisplayString,
    ntronPortsPortAdminStatus           INTEGER,
    ntronPortsPortFlowControl           INTEGER,
    ntronPortsPortPVID                  Integer32,
    ntronPortsPortAutoNegotiate         INTEGER,
    ntronPortsPortDuplex                INTEGER,
    ntronPortsPortSpeed                 INTEGER,
    ntronPortsPortCrossOver             INTEGER,
    ntronPortsPortQosDSCP               INTEGER,
    ntronPortsPortQos8021p              INTEGER,
    ntronPortsPortQosPriorityValue      Integer32,
    ntronPortsPortUsageAlarmLow         Integer32,
    ntronPortsPortUsageAlarmHigh        Integer32,
    ntronPortsPortPortNumberId          Integer32,
    ntronPortsPortPortUserDescription   DisplayString
}

ntronPortsPortPortNumber      	OBJECT-TYPE
    SYNTAX     			        DisplayString(SIZE(0..255))
	MAX-ACCESS         			read-write
    STATUS              		current
    DESCRIPTION 				"The port number."
    ::= {ntronPortsPort 1}

ntronPortsPortAdminStatus      	OBJECT-TYPE
    SYNTAX     			        INTEGER
								{
									disabled (1),
									enabled (2)
                                }
    	MAX-ACCESS          	read-write
    	STATUS              	current
    	DESCRIPTION		      	"This attribute allows an administrative request to
								disable or enable communications on this port."
    ::= {ntronPortsPort 2}

ntronPortsPortFlowControl      	OBJECT-TYPE
    SYNTAX     			        INTEGER
								{
									autoNegotiate (1),
									enabled (2),
									disabled(3)
                                }
   	MAX-ACCESS  	        	read-write
   	STATUS          	    	current
   	DESCRIPTION		    	  	"Flow control status of each port. When enabled,
								the port supports half-duplex back pressure and
								full-duplex flow control."
    ::= {ntronPortsPort 3}

ntronPortsPortPVID				OBJECT-TYPE
   	SYNTAX						Integer32(1..4094)
   	MAX-ACCESS					read-write
   	STATUS						current
   	DESCRIPTION					"The VLAN ID assigned to ingressed untagged frames, or
								all ingressed frames if 'Replace Ingress VID Tag with
								Default Port VID' is enabled."
   	::= { ntronPortsPort 4 }

ntronPortsPortAutoNegotiate    	OBJECT-TYPE
    SYNTAX     			        INTEGER
								{
									disabled (1),
									enabled (2)
                                }
   	MAX-ACCESS  	        	read-write
   	STATUS          	    	current
   	DESCRIPTION				 	"This per-port attribute describes whether the port identified
								has AutoNegotiation  Enabled or not."
    ::= {ntronPortsPort 5}

ntronPortsPortDuplex    	OBJECT-TYPE
    SYNTAX  		        INTEGER
							{
								half (1),
								full (2)
                            }
   	MAX-ACCESS 	        	read-write
   	STATUS         	    	current
   	DESCRIPTION		    	"The existing mode of the port whether it is Full Duplex/Half Duplex."
    ::= {ntronPortsPort 6}

ntronPortsPortSpeed    	OBJECT-TYPE
    SYNTAX     	        INTEGER
						{
							portSpeed10 	(2),
							portSpeed100 	(3),
							portSpeed1000	(5)
                        }
   	MAX-ACCESS  	   	read-write
   	STATUS            	current
   	DESCRIPTION		   	"This is the port setting for speed."
    ::= {ntronPortsPort 7}

ntronPortsPortCrossOver    	OBJECT-TYPE
    SYNTAX    		        INTEGER
							{
								auto 	(1),
								yes 	(2),
								no		(3)
                            }
   	MAX-ACCESS  	       	read-write
   	STATUS          	   	current
   	DESCRIPTION		   		"This is the port setting for Crossover."
    ::= {ntronPortsPort 8}

ntronPortsPortQosDSCP    	OBJECT-TYPE
    SYNTAX  		        INTEGER
							{
								disabled (1),
								enabled (2)
                            }
   	MAX-ACCESS  	        read-write
   	STATUS          	    current
   	DESCRIPTION		    	"The status of whether or not to include the ingress
							frame's RFC 2474 DSCP value in determining the transmit
							priority and egress frame's IEEE802.1p User Priority value."
    ::= {ntronPortsPort 9}

ntronPortsPortQos8021p  OBJECT-TYPE
    SYNTAX     			    INTEGER
							{
								disabled (1),
								enabled (2)
                            }
   	MAX-ACCESS  	        read-write
   	STATUS          	    current
   	DESCRIPTION		    	"The status of whether or not to include the ingress frame's
							IEEE802.1p User Priority value in determining the transmit
							priority and egress frame's IEEE802.1p User Priority value."
    ::= {ntronPortsPort 10}

ntronPortsPortQosPriorityValue    	OBJECT-TYPE
    SYNTAX     			        	Integer32
   	MAX-ACCESS  	        		read-write
   	STATUS          	    		current
   	DESCRIPTION		    			"The default QOS priority for the transmit priority value and the
									egress frame's IEEE802.1p User Priority value if not otherwise
									assigned by DSCP or IEEE802.1p processing."
    ::= {ntronPortsPort 11}

ntronPortsPortUsageAlarmLow		OBJECT-TYPE
   	SYNTAX						Integer32(0..100)
   	MAX-ACCESS					read-write
   	STATUS						current
   	DESCRIPTION					"The bandwidth utilization percentage below which a fault will
								be triggered if enabled."
   	::= { ntronPortsPort 12 }

ntronPortsPortUsageAlarmHigh	OBJECT-TYPE
   	SYNTAX						Integer32(0..100)
   	MAX-ACCESS					read-write
   	STATUS						current
   	DESCRIPTION					"The bandwidth utilization percentage above which a fault will be
								triggered if enabled."
   	::= { ntronPortsPort 13 }

ntronPortsPortPortNumberId  	OBJECT-TYPE
    SYNTAX     			        Integer32
   	MAX-ACCESS  	        	read-only
   	STATUS          	    	current
   	DESCRIPTION		    	  	"The port number Id."
    ::= {ntronPortsPort 14}

ntronPortsPortPortUserDescription   OBJECT-TYPE
    SYNTAX                          DisplayString(SIZE(0..64))
    MAX-ACCESS                      read-write
    STATUS                          current
    DESCRIPTION                     "Description of the port set by a user."
    ::= {ntronPortsPort 15}

--  ----------------------------------------------------------------------------------
ntronPortStatus   OBJECT IDENTIFIER  	::= {ntronPortGroup 20}
--  ----------------------------------------------------------------------------------

ntronPortsStatusTable     		OBJECT-TYPE
   	SYNTAX    	         		SEQUENCE OF NtronPortsStatus
	MAX-ACCESS  	        	not-accessible
   	STATUS          	       	current
   	DESCRIPTION  				""
	::= { ntronPortStatus 1 }

ntronPortsStatusPort	  		OBJECT-TYPE
    SYNTAX                		NtronPortsStatus
    MAX-ACCESS            		not-accessible
    STATUS                		current
    DESCRIPTION					"An entry in the ntronPortsStatusTable."
	INDEX      					{ntronPortsStatusPortPortNumberId }
    ::= {ntronPortsStatusTable 1 }

NtronPortsStatus ::= SEQUENCE {
	ntronPortsStatusPortPortNumber		DisplayString,
    ntronPortsStatusPortLink	 		INTEGER,
	ntronPortsStatusPortDuplex	 		INTEGER,
	ntronPortsStatusPortSpeed			INTEGER,
	ntronPortsStatusPortFlowControl		INTEGER,
	ntronPortsStatusPortCrossover		INTEGER,
	ntronPortsStatusPortState			INTEGER,
	ntronPortsStatusPortPortNumberId	Integer32
}

ntronPortsStatusPortPortNumber      	OBJECT-TYPE
    SYNTAX     			        DisplayString(SIZE(0..255))
	MAX-ACCESS         			read-only
    STATUS              		current
    DESCRIPTION 				"The port number"
    ::= {ntronPortsStatusPort 1}

ntronPortsStatusPortLink      	OBJECT-TYPE
    SYNTAX     			        INTEGER
								{
									enabled (1),
									disabled(2)
                                }
    	MAX-ACCESS          	read-only
    	STATUS              	current
    	DESCRIPTION		      	"The current link status of the port."
    ::= {ntronPortsStatusPort 2}

ntronPortsStatusPortDuplex    	OBJECT-TYPE
    SYNTAX  		        INTEGER
							{
								half (1),
								full (2)
                            }
   	MAX-ACCESS 	        	read-only
   	STATUS         	    	current
   	DESCRIPTION		    	"The existing mode of the port whether it is Full Duplex/Half Duplex."
    ::= {ntronPortsStatusPort 3}

ntronPortsStatusPortSpeed    	OBJECT-TYPE
    SYNTAX     	        INTEGER
						{
							portSpeed10 	(2),
							portSpeed100 	(3),
							portSpeed1000	(5)
                        }
   	MAX-ACCESS  	   	read-only
   	STATUS            	current
   	DESCRIPTION		   	"This current port speed."
    ::= {ntronPortsStatusPort 4}

ntronPortsStatusPortFlowControl      	OBJECT-TYPE
    SYNTAX     			        INTEGER
								{
									autoNegotiate (1),
									enabled (2),
									disabled(3)
                                }
   	MAX-ACCESS  	        	read-write
   	STATUS          	    	current
   	DESCRIPTION		    	  	"Flow control status of each port. When enabled,
								the port supports half-duplex back pressure and
								full-duplex flow control."
    ::= {ntronPortsStatusPort 5}

ntronPortsStatusPortCrossover  OBJECT-TYPE
    SYNTAX     			    INTEGER
							{
								auto 	(1),
								yes 	(2),
								no		(3)
                            }
   	MAX-ACCESS  	        read-only
   	STATUS          	    current
   	DESCRIPTION		    	""
    ::= {ntronPortsStatusPort 6}

ntronPortsStatusPortState  OBJECT-TYPE
    SYNTAX     			    INTEGER
							{
								forwardingNoStp(1),
								disabled 	(2),
								blocking	(3),
								listening 	(5),
								learning	(9),
								forwarding	(17)
                            }
   	MAX-ACCESS  	        read-only
   	STATUS          	    current
   	DESCRIPTION		    	"The current status of the port."
    ::= {ntronPortsStatusPort 7}

ntronPortsStatusPortPortNumberId  	OBJECT-TYPE
    SYNTAX     			        Integer32
   	MAX-ACCESS  	        	read-only
   	STATUS          	    	current
   	DESCRIPTION		    	  	"The port number Id."
    ::= {ntronPortsStatusPort 8}

--  ----------------------------------------------------------------------------------
--
--	MirrorGroup
--
--  ----------------------------------------------------------------------------------

--  ----------------------------------------------------------------------------------
ntronMirrorConfig   OBJECT IDENTIFIER  	::= {ntronMirrorGroup 10}
--  ----------------------------------------------------------------------------------

ntronMirrorConfigStatus     OBJECT-TYPE
    SYNTAX               	INTEGER
							{
                            	disabled (1),
                            	enabled  (2)
                            }
	MAX-ACCESS          	read-write
	STATUS              	current
	DESCRIPTION 			"The existing status of the Mirroring whether it is
							enabled or disabled."
    ::= { ntronMirrorConfig 1 }

ntronMirrorConfigMirroredDataOnly	OBJECT-TYPE
    SYNTAX               			INTEGER
									{
										disabled (1),
										enabled  (2)
									}
	MAX-ACCESS   			       	read-write
	STATUS              			current
	DESCRIPTION 					"If this is enabled, only mirrored data will be
									transmitted by the destination port."
    ::= { ntronMirrorConfig 2 }

ntronMirrorConfigDestination	OBJECT-TYPE
    SYNTAX              		DisplayString(SIZE(0..255))
    MAX-ACCESS          		read-write
    STATUS              		current
    DESCRIPTION 				"The destination port mirrored to."
    ::= { ntronMirrorConfig 3 }

ntronMirrorConfigRxSourcePorts	OBJECT-TYPE
    SYNTAX              		DisplayString(SIZE(0..255))
    MAX-ACCESS          		read-write
    STATUS              		current
    DESCRIPTION 				"The source ports configured to mirror frames that are
								received."
    ::= { ntronMirrorConfig 4 }

ntronMirrorConfigTxSourcePorts	OBJECT-TYPE
    SYNTAX              		DisplayString(SIZE(0..255))
    MAX-ACCESS          		read-write
    STATUS              		current
    DESCRIPTION 				"The source ports configured to mirror frames that are
								transmitted."
    ::= { ntronMirrorConfig 5 }

--  ----------------------------------------------------------------------------------
--
--	TrunkGroup
--
--  ----------------------------------------------------------------------------------

--  ----------------------------------------------------------------------------------
ntronTrunkConfig   OBJECT IDENTIFIER  	::= {ntronTrunkGroup 10}
--  ----------------------------------------------------------------------------------

ntronTrunksTable     			OBJECT-TYPE
   	SYNTAX    	         		SEQUENCE OF NtronTrunks
	MAX-ACCESS  	        	not-accessible
   	STATUS          	       	current
   	DESCRIPTION  				""
	::= { ntronTrunkConfig 1 }

ntronTrunksTrunk	  			OBJECT-TYPE
    SYNTAX                		NtronTrunks
    MAX-ACCESS            		not-accessible
    STATUS                		current
    DESCRIPTION					"An entry in the ntronTrunksTable."
	INDEX      					{ntronTrunksTrunkId }
    ::= {ntronTrunksTable 1 }

NtronTrunks ::= SEQUENCE {
	ntronTrunksTrunkId			Integer32,
    ntronTrunksTrunkName	 	DisplayString,
	ntronTrunksTrunkPorts	 	DisplayString,
	ntronTrunksTrunkStatus		INTEGER
}

ntronTrunksTrunkId  			OBJECT-TYPE
    SYNTAX     			        Integer32(1..127)
   	MAX-ACCESS  	        	read-write
   	STATUS          	    	current
   	DESCRIPTION		    	  	"The trunk identifier number."
    ::= {ntronTrunksTrunk 1}

ntronTrunksTrunkName			OBJECT-TYPE
    SYNTAX              		DisplayString(SIZE(0..255))
    MAX-ACCESS          		read-write
    STATUS              		current
    DESCRIPTION 				"The descriptive name of the trunk.  The name
								can consist of alphanumeric characters and the
								special characters '#', '_', '-', and '.'."
    ::= { ntronTrunksTrunk 2 }

ntronTrunksTrunkPorts			OBJECT-TYPE
    SYNTAX              		DisplayString(SIZE(0..255))
    MAX-ACCESS          		read-write
    STATUS              		current
    DESCRIPTION 				"The ports associated with the trunk."
    ::= { ntronTrunksTrunk 3 }

ntronTrunksTrunkStatus				OBJECT-TYPE
    SYNTAX               			INTEGER
									{
										disabled (1),
										enabled  (2)
									}
	MAX-ACCESS   			       	read-write
	STATUS              			current
	DESCRIPTION 					"The existing status of the trunk. It can be
									either enabled or disabled."
    ::= { ntronTrunksTrunk 4 }

--  ----------------------------------------------------------------------------------
--
--	PortStatsGroup
--
--  ----------------------------------------------------------------------------------

--  ----------------------------------------------------------------------------------
ntronPortStatsList   OBJECT IDENTIFIER  	::= {ntronPortGroup 40}
--  ----------------------------------------------------------------------------------

ntronPortsStatsTable     		OBJECT-TYPE
   	SYNTAX    	         		SEQUENCE OF NtronPortsStats
	MAX-ACCESS  	        	not-accessible
   	STATUS          	       	current
   	DESCRIPTION  				""
	::= { ntronPortStatsList 1 }

ntronPortsStatsPort	  			OBJECT-TYPE
    SYNTAX                		NtronPortsStats
    MAX-ACCESS            		not-accessible
    STATUS                		current
    DESCRIPTION					"An entry in the ntronPortStatsTable."
	INDEX      					{ntronPortsStatsPortPortNumberId }
    ::= {ntronPortsStatsTable 1 }

NtronPortsStats ::= SEQUENCE {
	ntronPortsStatsPortPortNumber				DisplayString,
	ntronPortsStatsPortTxOctets                 Counter32,
	ntronPortsStatsPortTxDropPkts               Counter32,
	ntronPortsStatsPortTxBroadcastPkts          Counter32,
	ntronPortsStatsPortTxMulticastPkts          Counter32,
	ntronPortsStatsPortTxUnicastPkts            Counter32,
	ntronPortsStatsPortTxCollisions             Counter32,
	ntronPortsStatsPortTxSingleCollision        Counter32,
	ntronPortsStatsPortTxMultipleCollision      Counter32,
	ntronPortsStatsPortTxDeferredTransmit       Counter32,
	ntronPortsStatsPortTxLateCollision          Counter32,
	ntronPortsStatsPortTxExcessiveCollision     Counter32,
	ntronPortsStatsPortTxFrameInDisc            Counter32,
	ntronPortsStatsPortTxPausePkts              Counter32,
	ntronPortsStatsPortRxOctets                 Counter32,
	ntronPortsStatsPortRxUndersizePkts          Counter32,
	ntronPortsStatsPortRxPausePkts              Counter32,
	ntronPortsStatsPortPkts64Octets             Counter32,
	ntronPortsStatsPortPkts65to127Octets        Counter32,
	ntronPortsStatsPortPkts128to255Octets       Counter32,
	ntronPortsStatsPortPkts256to511Octets       Counter32,
	ntronPortsStatsPortPkts512to1023Octets      Counter32,
	ntronPortsStatsPortPkts1024toMaxOctets      Counter32,
	ntronPortsStatsPortRxOversizePkts           Counter32,
	ntronPortsStatsPortRxJabbers                Counter32,
	ntronPortsStatsPortRxAlignmentErrors        Counter32,
	ntronPortsStatsPortRxFcsErrors              Counter32,
	ntronPortsStatsPortRxGoodOctets             Counter32,
	ntronPortsStatsPortRxDropPkts               Counter32,
	ntronPortsStatsPortRxUnicastPkts            Counter32,
	ntronPortsStatsPortRxMulticastPkts          Counter32,
	ntronPortsStatsPortRxBroadcastPkts          Counter32,
	ntronPortsStatsPortRxSAChanges              Counter32,
	ntronPortsStatsPortRxFragments              Counter32,
	ntronPortsStatsPortRxExcessiveDisc          Counter32,
	ntronPortsStatsPortRxSymbolError            Counter32,
	ntronPortsStatsPortRxBadOctets              Counter32,
	ntronPortsStatsPortPortNumberId				Integer32
}

ntronPortsStatsPortPortNumber   OBJECT-TYPE
    SYNTAX     			        DisplayString(SIZE(0..255))
	MAX-ACCESS         			read-only
    STATUS              		current
    DESCRIPTION 				"The port number."
    ::= {ntronPortsStatsPort 1}

ntronPortsStatsPortTxOctets     OBJECT-TYPE
    SYNTAX     			        Counter32
    	MAX-ACCESS          	read-only
    	STATUS              	current
    	DESCRIPTION		      	"Transmit octets counter for the port."
    ::= {ntronPortsStatsPort 2}

ntronPortsStatsPortTxDropPkts   OBJECT-TYPE
    SYNTAX     			        Counter32
    	MAX-ACCESS          	read-only
    	STATUS              	current
    	DESCRIPTION		      	"Transmit drop packets counter for the port."
    ::= {ntronPortsStatsPort 3}

ntronPortsStatsPortTxBroadcastPkts   OBJECT-TYPE
    SYNTAX     			        Counter32
    	MAX-ACCESS          	read-only
    	STATUS              	current
    	DESCRIPTION		      	"Transmit broadcast packets counter for the port."
    ::= {ntronPortsStatsPort 4}

ntronPortsStatsPortTxMulticastPkts   OBJECT-TYPE
    SYNTAX     			        Counter32
    	MAX-ACCESS          	read-only
    	STATUS              	current
    	DESCRIPTION		      	"Transmit multicast packets counter for the port."
    ::= {ntronPortsStatsPort 5}

ntronPortsStatsPortTxUnicastPkts   OBJECT-TYPE
    SYNTAX     			        Counter32
    	MAX-ACCESS          	read-only
    	STATUS              	current
    	DESCRIPTION		      	"Transmit unicast packets counter for the port."
    ::= {ntronPortsStatsPort 6}

ntronPortsStatsPortTxCollisions   OBJECT-TYPE
    SYNTAX     			        Counter32
    	MAX-ACCESS          	read-only
    	STATUS              	current
    	DESCRIPTION		      	"Transmit collisions counter for the port."
    ::= {ntronPortsStatsPort 7}

ntronPortsStatsPortTxSingleCollision   OBJECT-TYPE
    SYNTAX     			        Counter32
    	MAX-ACCESS          	read-only
    	STATUS              	current
    	DESCRIPTION		      	"Transmit single collisions counter for the port."
    ::= {ntronPortsStatsPort 8}

ntronPortsStatsPortTxMultipleCollision   OBJECT-TYPE
    SYNTAX     			        Counter32
    	MAX-ACCESS          	read-only
    	STATUS              	current
    	DESCRIPTION		      	"Transmit multiple collisions counter for the port."
    ::= {ntronPortsStatsPort 9}

ntronPortsStatsPortTxDeferredTransmit   OBJECT-TYPE
    SYNTAX     			        Counter32
    	MAX-ACCESS          	read-only
    	STATUS              	current
    	DESCRIPTION		      	"Transmit deferred counter for the port."
    ::= {ntronPortsStatsPort 10}

ntronPortsStatsPortTxLateCollision   OBJECT-TYPE
    SYNTAX     			        Counter32
    	MAX-ACCESS          	read-only
    	STATUS              	current
    	DESCRIPTION		      	"Transmit late collision counter for the port."
    ::= {ntronPortsStatsPort 11}

ntronPortsStatsPortTxExcessiveCollision   OBJECT-TYPE
    SYNTAX     			        Counter32
    	MAX-ACCESS          	read-only
    	STATUS              	current
    	DESCRIPTION		      	"Transmit excessive collision counter for the port."
    ::= {ntronPortsStatsPort 12}

ntronPortsStatsPortTxFrameInDisc   OBJECT-TYPE
    SYNTAX     			        Counter32
    	MAX-ACCESS          	read-only
    	STATUS              	current
    	DESCRIPTION		      	"Transmit frame in discard counter for the port."
    ::= {ntronPortsStatsPort 13}

ntronPortsStatsPortTxPausePkts   OBJECT-TYPE
    SYNTAX     			        Counter32
    	MAX-ACCESS          	read-only
    	STATUS              	current
    	DESCRIPTION		      	"Transmit pause packets counter for the port."
    ::= {ntronPortsStatsPort 14}

ntronPortsStatsPortRxOctets   OBJECT-TYPE
    SYNTAX     			        Counter32
    	MAX-ACCESS          	read-only
    	STATUS              	current
    	DESCRIPTION		      	"Receive octets counter for the port."
    ::= {ntronPortsStatsPort 15}

ntronPortsStatsPortRxUndersizePkts   OBJECT-TYPE
    SYNTAX     			        Counter32
    	MAX-ACCESS          	read-only
    	STATUS              	current
    	DESCRIPTION		      	"Receive undersize packets counter for the port."
    ::= {ntronPortsStatsPort 16}

ntronPortsStatsPortRxPausePkts   OBJECT-TYPE
    SYNTAX     			        Counter32
    	MAX-ACCESS          	read-only
    	STATUS              	current
    	DESCRIPTION		      	"Receive pause packets counter for the port."
    ::= {ntronPortsStatsPort 17}

ntronPortsStatsPortPkts64Octets   OBJECT-TYPE
    SYNTAX     			        Counter32
    	MAX-ACCESS          	read-only
    	STATUS              	current
    	DESCRIPTION		      	"Receive 64 octets counter for the port."
    ::= {ntronPortsStatsPort 18}

ntronPortsStatsPortPkts65to127Octets   OBJECT-TYPE
    SYNTAX     			        Counter32
    	MAX-ACCESS          	read-only
    	STATUS              	current
    	DESCRIPTION		      	"Receive 65 to 127 octets counter for the port."
    ::= {ntronPortsStatsPort 19}

ntronPortsStatsPortPkts128to255Octets   OBJECT-TYPE
    SYNTAX     			        Counter32
    	MAX-ACCESS          	read-only
    	STATUS              	current
    	DESCRIPTION		      	"Receive 128 to 255 octets counter for the port."
    ::= {ntronPortsStatsPort 20}

ntronPortsStatsPortPkts256to511Octets   OBJECT-TYPE
    SYNTAX     			        Counter32
    	MAX-ACCESS          	read-only
    	STATUS              	current
    	DESCRIPTION		      	"Receive 256 to 511 octets counter for the port."
    ::= {ntronPortsStatsPort 21}

ntronPortsStatsPortPkts512to1023Octets   OBJECT-TYPE
    SYNTAX     			        Counter32
    	MAX-ACCESS          	read-only
    	STATUS              	current
    	DESCRIPTION		      	"Receive 512 to 1023 octets counter for the port."
    ::= {ntronPortsStatsPort 22}

ntronPortsStatsPortPkts1024toMaxOctets   OBJECT-TYPE
    SYNTAX     			        Counter32
    	MAX-ACCESS          	read-only
    	STATUS              	current
    	DESCRIPTION		      	"Receive 1024 or larger octets counter for the port."
    ::= {ntronPortsStatsPort 23}

ntronPortsStatsPortRxOversizePkts   OBJECT-TYPE
    SYNTAX     			        Counter32
    	MAX-ACCESS          	read-only
    	STATUS              	current
    	DESCRIPTION		      	"Receive oversize packets counter for the port."
    ::= {ntronPortsStatsPort 24}

ntronPortsStatsPortRxJabbers   OBJECT-TYPE
    SYNTAX     			        Counter32
    	MAX-ACCESS          	read-only
    	STATUS              	current
    	DESCRIPTION		      	"Receive jabbers counter for the port."
    ::= {ntronPortsStatsPort 25}

ntronPortsStatsPortRxAlignmentErrors   OBJECT-TYPE
    SYNTAX     			        Counter32
    	MAX-ACCESS          	read-only
    	STATUS              	current
    	DESCRIPTION		      	"Receive alignment errors counter for the port."
    ::= {ntronPortsStatsPort 26}

ntronPortsStatsPortRxFcsErrors   OBJECT-TYPE
    SYNTAX     			        Counter32
    	MAX-ACCESS          	read-only
    	STATUS              	current
    	DESCRIPTION		      	"Receive FCS errors counter for the port."
    ::= {ntronPortsStatsPort 27}

ntronPortsStatsPortRxGoodOctets   OBJECT-TYPE
    SYNTAX     			        Counter32
    	MAX-ACCESS          	read-only
    	STATUS              	current
    	DESCRIPTION		      	"Receive good octets counter for the port."
    ::= {ntronPortsStatsPort 28}

ntronPortsStatsPortRxDropPkts   OBJECT-TYPE
    SYNTAX     			        Counter32
    	MAX-ACCESS          	read-only
    	STATUS              	current
    	DESCRIPTION		      	"Receive drop packets counter for the port."
    ::= {ntronPortsStatsPort 29}

ntronPortsStatsPortRxUnicastPkts   OBJECT-TYPE
    SYNTAX     			        Counter32
    	MAX-ACCESS          	read-only
    	STATUS              	current
    	DESCRIPTION		      	"Receive unicast packets counter for the port."
    ::= {ntronPortsStatsPort 30}

ntronPortsStatsPortRxMulticastPkts   OBJECT-TYPE
    SYNTAX     			        Counter32
    	MAX-ACCESS          	read-only
    	STATUS              	current
    	DESCRIPTION		      	"Receive multicast packets counter for the port."
    ::= {ntronPortsStatsPort 31}

ntronPortsStatsPortRxBroadcastPkts   OBJECT-TYPE
    SYNTAX     			        Counter32
    	MAX-ACCESS          	read-only
    	STATUS              	current
    	DESCRIPTION		      	"Receive broadcast packets counter for the port."
    ::= {ntronPortsStatsPort 32}

ntronPortsStatsPortRxSAChanges   OBJECT-TYPE
    SYNTAX     			        Counter32
    	MAX-ACCESS          	read-only
    	STATUS              	current
    	DESCRIPTION		      	"Receive source address changes counter for the port."
    ::= {ntronPortsStatsPort 33}

ntronPortsStatsPortRxFragments   OBJECT-TYPE
    SYNTAX     			        Counter32
    	MAX-ACCESS          	read-only
    	STATUS              	current
    	DESCRIPTION		      	"Receive fragments counter for the port."
    ::= {ntronPortsStatsPort 34}

ntronPortsStatsPortRxExcessiveDisc   OBJECT-TYPE
    SYNTAX     			        Counter32
    	MAX-ACCESS          	read-only
    	STATUS              	current
    	DESCRIPTION		      	"Receive excessive discards counter for the port."
    ::= {ntronPortsStatsPort 35}

ntronPortsStatsPortRxSymbolError   OBJECT-TYPE
    SYNTAX     			        Counter32
    	MAX-ACCESS          	read-only
    	STATUS              	current
    	DESCRIPTION		      	"Receive symbol errors counter for the port."
    ::= {ntronPortsStatsPort 36}

ntronPortsStatsPortRxBadOctets   OBJECT-TYPE
    SYNTAX     			        Counter32
    	MAX-ACCESS          	read-only
    	STATUS              	current
    	DESCRIPTION		      	"Receive bad octets counter for the port."
    ::= {ntronPortsStatsPort 37}

ntronPortsStatsPortPortNumberId  	OBJECT-TYPE
    SYNTAX     			        Integer32(1..64)
   	MAX-ACCESS  	        	read-only
   	STATUS          	    	current
   	DESCRIPTION		    	  	"The port number Id."
    ::= {ntronPortsStatsPort 38}

--  ----------------------------------------------------------------------------------
--
--	RateLimitGroup
--
--  ----------------------------------------------------------------------------------

--  ----------------------------------------------------------------------------------
ntronRateLimitConfig  OBJECT IDENTIFIER  	::= {ntronRateLimitGroup 10}
--  ----------------------------------------------------------------------------------

ntronRateLimitListTable     	OBJECT-TYPE
   	SYNTAX    	         		SEQUENCE OF NtronRateLimitList
	MAX-ACCESS  	        	not-accessible
   	STATUS          	       	current
   	DESCRIPTION  				"Rate limiting table"
	::= { ntronRateLimitConfig 1 }

ntronRateLimitsLimit	  		OBJECT-TYPE
    SYNTAX                		NtronRateLimitList
    MAX-ACCESS            		not-accessible
    STATUS                		current
    DESCRIPTION					"An entry in the ntronRateLimitListTable."
	INDEX      					{ntronRateLimitsLimitPortNumberId }
    ::= {ntronRateLimitListTable 1 }

NtronRateLimitList ::= SEQUENCE {
	ntronRateLimitsLimitPortNumber		DisplayString,
    ntronRateLimitsLimitRateLimit	 	Integer32,
	ntronRateLimitsLimitBroadcast	 	INTEGER,
	ntronRateLimitsLimitMulticast		INTEGER,
	ntronRateLimitsLimitUnknownUnicast	INTEGER,
	ntronRateLimitsLimitKnownUnicast	INTEGER,
	ntronRateLimitsLimitPortNumberId	Integer32
}

ntronRateLimitsLimitPortNumber  OBJECT-TYPE
    SYNTAX     			        DisplayString(SIZE(0..255))
	MAX-ACCESS         			read-write
    STATUS              		current
    DESCRIPTION 				"The port number"
    ::= {ntronRateLimitsLimit 1}

ntronRateLimitsLimitRateLimit	OBJECT-TYPE
   	SYNTAX						Integer32(0..100)
   	MAX-ACCESS					read-write
   	STATUS						current
   	DESCRIPTION					"The ingress traffic rate. The allowed range is 0-100
								and the default is: 3%. 100% is not limiting."
   	::= { ntronRateLimitsLimit 2 }

ntronRateLimitsLimitBroadcast		OBJECT-TYPE
    SYNTAX               			INTEGER
									{
										disabled (1),
										enabled  (2)
									}
	MAX-ACCESS   			       	read-write
	STATUS              			current
	DESCRIPTION 					"Enable/disable limiting on broadcast packets."
    ::= { ntronRateLimitsLimit 3 }

ntronRateLimitsLimitMulticast		OBJECT-TYPE
    SYNTAX               			INTEGER
									{
										disabled (1),
										enabled  (2)
									}
	MAX-ACCESS   			       	read-write
	STATUS              			current
	DESCRIPTION 					"Enable/disable limiting on multicast packets."
    ::= { ntronRateLimitsLimit 4 }

ntronRateLimitsLimitUnknownUnicast	OBJECT-TYPE
    SYNTAX               			INTEGER
									{
										disabled (1),
										enabled  (2)
									}
	MAX-ACCESS   			       	read-write
	STATUS              			current
	DESCRIPTION 					"Enable/disable limiting on unknown unicast packets."
    ::= { ntronRateLimitsLimit 5 }

ntronRateLimitsLimitKnownUnicast	OBJECT-TYPE
    SYNTAX               			INTEGER
									{
										disabled (1),
										enabled  (2)
									}
	MAX-ACCESS   			       	read-write
	STATUS              			current
	DESCRIPTION 					"Enable/disable limiting on known unicast packets."
    ::= { ntronRateLimitsLimit 6 }

ntronRateLimitsLimitPortNumberId	OBJECT-TYPE
    SYNTAX     			        	Integer32
   	MAX-ACCESS  	        		read-only
   	STATUS          	    		current
   	DESCRIPTION		    	  		"The port number Id."
    ::= {ntronRateLimitsLimit 7}

--  ----------------------------------------------------------------------------------
--
--  RstpGroup
--
--  ----------------------------------------------------------------------------------

--  ----------------------------------------------------------------------------------
ntronRstpConfig   OBJECT IDENTIFIER     ::= {ntronRstpGroup 10}
--  ----------------------------------------------------------------------------------

--  ----------------------------------------------------------------------------------
ntronRstpBridge   OBJECT IDENTIFIER     ::= {ntronRstpConfig 1}
--  ----------------------------------------------------------------------------------
ntronRstpBridgeWebStatus    OBJECT-TYPE
    SYNTAX                  INTEGER
                            {
                                disabled    (3),
                                forceStp    (5),
                                rstp        (7)
                            }
    MAX-ACCESS              read-write
    STATUS                  current
    DESCRIPTION             "This is the configured RSTP protocol on this bridge."
    ::= { ntronRstpBridge 1 }

ntronRstpBridgeVlanId           OBJECT-TYPE
    SYNTAX                      Integer32(1..4094)
    MAX-ACCESS                  read-write
    STATUS                      current
    DESCRIPTION                 "RSTP will operate on all ports of the indicated VLAN"
    ::= {ntronRstpBridge 2}

ntronRstpBridgeBridgePriorityStep       OBJECT-TYPE
    SYNTAX                      INTEGER
                                {
                                    priority0       (1),
                                    priority4096    (2),
                                    priority8192    (3),
                                    priority12288   (4),
                                    priority16384   (5),
                                    priority20480   (6),
                                    priority24576   (7),
                                    priority28672   (8),
                                    priority32768   (9),
                                    priority36864   (10),
                                    priority40960   (11),
                                    priority45056   (12),
                                    priority49152   (13),
                                    priority53248   (14),
                                    priority57344   (15),
                                    priority61440   (16)
                                }
    MAX-ACCESS                  read-write
    STATUS                      current
    DESCRIPTION                 "The Priority of this Bridge."
    ::= {ntronRstpBridge 3}

ntronRstpBridgeMacAddress       OBJECT-TYPE
    SYNTAX                      DisplayString(SIZE(0..255))
    MAX-ACCESS                  read-only
    STATUS                      current
    DESCRIPTION                 "This object will return the MAC address of this Bridge."
    ::= { ntronRstpBridge 4 }

ntronRstpBridgeHelloTime        OBJECT-TYPE
    SYNTAX                      Integer32(1..10)
    MAX-ACCESS                  read-write
    STATUS                      current
    DESCRIPTION                 "This is the time interval, in seconds, between the transmission
                                of Configuration BPDUs by Designated Ports."
    ::= {ntronRstpBridge 5}

ntronRstpBridgeFowardDelay      OBJECT-TYPE
    SYNTAX                      Integer32(4..30)
    MAX-ACCESS                  read-write
    STATUS                      current
    DESCRIPTION                 "This is the time spent, in seconds, by legacy STP Bridges in transitioning
                                Root and Designated Ports to Forwarding. This delays Port transitions until
                                other bridges have received spanning tree information."
    ::= {ntronRstpBridge 6}

ntronRstpBridgeMaxAge   OBJECT-TYPE
    SYNTAX                      Integer32(6..40)
    MAX-ACCESS                  read-write
    STATUS                      current
    DESCRIPTION                 "For RSTP: this is the maximum hops allowed for any protocol message
                                before it is discarded and no longer retransmitted.
                                For STP: this is the maximum time, in seconds, that a bridge will wait
                                for Configuration BPDUs before deciding it is no longer connected to
                                the root bridge."
    ::= {ntronRstpBridge 7}

ntronRstpBridgeTxHoldCount      OBJECT-TYPE
    SYNTAX                      Integer32(1..10)
    MAX-ACCESS                  read-write
    STATUS                      current
    DESCRIPTION                 "The maximum number of Configuration BPDUs that
                                can be transmitted in one second, from a port
                                on this Bridge before transmission is throttled. "
    ::= {ntronRstpBridge 8}

ntronRstpBridgeTopologyChanges  OBJECT-TYPE
    SYNTAX                      Integer32
    MAX-ACCESS                  read-only
    STATUS                      current
    DESCRIPTION                 "The number of RSTP topology changes since the switch has been powered
                                on or rebooted"
    ::= {ntronRstpBridge 9}

ntronRstpCurrentStatus  OBJECT-TYPE
    SYNTAX                  INTEGER
                            {
                                disabled    (3),
                                forceStp    (5),
                                rstp        (7)
                            }
    MAX-ACCESS              read-write
    STATUS                  current
    DESCRIPTION             "This is the current RSTP protocol on this bridge."
    ::= { ntronRstpBridge 10 }

ntronRstpBridgeBpduFlooding  OBJECT-TYPE
    SYNTAX                      INTEGER
                                {
                                    block   (1),
                                    flood   (2)
                                }
    MAX-ACCESS                  read-write
    STATUS                      current
    DESCRIPTION                 "This value allows the flooding or blocking
                                 of BPDUs to other ports when the global
                                 spanning tree is disabled or when spanning
                                 tree is disabled on a specific port.
                                 If flood is selected, BPDUs are flooded to
                                 all other ports based on the VLAN assignment.
                                 The options are block(1) or flood(2).
                                 The default is flood(2)."
    ::= {ntronRstpBridge 11}

ntronRstpPortsTable             OBJECT-TYPE
    SYNTAX                      SEQUENCE OF NtronRstpPorts
    MAX-ACCESS                  not-accessible
    STATUS                      current
    DESCRIPTION                 "RSTP Ports table"
    ::= { ntronRstpConfig 2 }

ntronRstpPortsPort              OBJECT-TYPE
    SYNTAX                      NtronRstpPorts
    MAX-ACCESS                  not-accessible
    STATUS                      current
    DESCRIPTION                 "An entry in the ntronRstpPortsTable."
    INDEX                       {ntronRstpPortsPortPortNumberId }
    ::= {ntronRstpPortsTable 1 }

NtronRstpPorts ::= SEQUENCE {
    ntronRstpPortsPortNumber                DisplayString,
    ntronRstpPortsPortVlanId                Integer32,
    ntronRstpPortsPortState                 INTEGER,
    ntronRstpPortPortStpBpdu                INTEGER,
    ntronRstpPortsPortPathCost              Integer32,
    ntronRstpPortsPortCurrentPathCost       Integer32,
    ntronRstpPortsPortPortPriorityStep      INTEGER,
    ntronRstpPortsPortAdminEdge             INTEGER,
    ntronRstpPortsPortAutoEdge              INTEGER,
    ntronRstpPortsPortAdminPtpMac           INTEGER,
    ntronRstpPortsPortBridgePriorityStep    INTEGER,
    ntronRstpPortsPortBridgeMac             DisplayString,
    ntronRstpPortsPortPortDesignatedPort    Integer32,
    ntronRstpPortsPortPortNumberId          Integer32

}

ntronRstpPortsPortNumber        OBJECT-TYPE
    SYNTAX                      DisplayString(SIZE(0..255))
    MAX-ACCESS                      read-only
    STATUS                          current
    DESCRIPTION                     "The port number."
    ::= {ntronRstpPortsPort 1}

ntronRstpPortsPortVlanId        OBJECT-TYPE
    SYNTAX                      Integer32(1..4095)
    MAX-ACCESS                  read-only
    STATUS                      current
    DESCRIPTION                 " The VLAN Id of the bridge.  Note: 4095 indicates
                                port is not part of the RSTP VLAN."
    ::= { ntronRstpPortsPort 2 }

ntronRstpPortsPortState  OBJECT-TYPE
    SYNTAX                  INTEGER
                            {
                                forwardingNoStp(1),
                                disabled    (2),
                                blocking    (3),
                                listening   (5),
                                learning    (9),
                                forwarding  (17)
                            }
    MAX-ACCESS              read-only
    STATUS                  current
    DESCRIPTION             "The current status of the port."
    ::= {ntronRstpPortsPort 3}

ntronRstpPortPortStpBpdu        OBJECT-TYPE
    SYNTAX                  INTEGER
                            {
                                no (1),
                                yes  (2)
                            }
    MAX-ACCESS              read-only
    STATUS                  current
    DESCRIPTION             "Whether or not a legacy STP BPDU has been received on the port."
    ::= { ntronRstpPortsPort 4 }

ntronRstpPortsPortPathCost      OBJECT-TYPE
    SYNTAX                      Integer32(0..200000000)
    MAX-ACCESS                  read-write
    STATUS                      current
    DESCRIPTION                 "The configured path cost of the port."
    ::= { ntronRstpPortsPort 5 }

ntronRstpPortsPortCurrentPathCost   OBJECT-TYPE
    SYNTAX                          Integer32(0..200000000)
    MAX-ACCESS                      read-only
    STATUS                          current
    DESCRIPTION                     "The current path cost of the port."
    ::= { ntronRstpPortsPort 6 }

ntronRstpPortsPortPortPriorityStep  OBJECT-TYPE
    SYNTAX                      INTEGER
                                {
                                    priority0       (1),
                                    priority16      (2),
                                    priority32      (3),
                                    priority48      (4),
                                    priority64      (5),
                                    priority80      (6),
                                    priority96      (7),
                                    priority112     (8),
                                    priority128     (9),
                                    priority144     (10),
                                    priority160     (11),
                                    priority176     (12),
                                    priority192     (13),
                                    priority208     (14),
                                    priority224     (15),
                                    priority240     (16)
                                }

    MAX-ACCESS                  read-write
    STATUS                      current
    DESCRIPTION                 "The priority of the port."
    ::= { ntronRstpPortsPort 7 }

ntronRstpPortsPortAdminEdge OBJECT-TYPE
    SYNTAX                      INTEGER
                                {
                                    disabled (1),
                                    enabled  (2)
                                }
    MAX-ACCESS                  read-write
    STATUS                      current
    DESCRIPTION                 "Whether or not this port is treated as an Edge Port
                                and can immediately enter the Forwarding state.  If Enabled,
                                no BPDUs are expected to be received at the port. Enable
                                only when an end device is linked to this port"
    ::= { ntronRstpPortsPort 8 }

ntronRstpPortsPortAutoEdge      OBJECT-TYPE
    SYNTAX                      INTEGER
                                {
                                    disabled (1),
                                    enabled  (2)
                                }
    MAX-ACCESS                  read-write
    STATUS                      current
    DESCRIPTION                 "Whether or not to use a short timeout when waiting for BPDUs
                                before determining that this is an Edge Port (if no BPDUs are
                                received)."
    ::= { ntronRstpPortsPort 9 }

ntronRstpPortsPortAdminPtpMac   OBJECT-TYPE
    SYNTAX                      INTEGER
                                {
                                    auto        (1),
                                    forceTrue   (2),
                                    forceFalse  (3)
                                }
    MAX-ACCESS                  read-write
    STATUS                      current
    DESCRIPTION                 "Whether at most one other network port is attached to the port's LAN segment.
                                auto: full-duplex links are assumed to be point-to-point, half duplex are not
                                forceTrue/forceFalse: if the automatic determination would be wrong."
    ::= { ntronRstpPortsPort 10 }

ntronRstpPortsPortBridgePriorityStep        OBJECT-TYPE
    SYNTAX                      INTEGER
                                {
                                    priority0       (1),
                                    priority4096    (2),
                                    priority8192    (3),
                                    priority12288   (4),
                                    priority16384   (5),
                                    priority20480   (6),
                                    priority24576   (7),
                                    priority28672   (8),
                                    priority32768   (9),
                                    priority36864   (10),
                                    priority40960   (11),
                                    priority45056   (12),
                                    priority49152   (13),
                                    priority53248   (14),
                                    priority57344   (15),
                                    priority61440   (16)
                                }
    MAX-ACCESS                  read-write
    STATUS                      current
    DESCRIPTION                 "The Priority of the Designated Bridge associated with the port's LAN segment."
    ::= {ntronRstpPortsPort 11}

ntronRstpPortsPortBridgeMac     OBJECT-TYPE
    SYNTAX                      DisplayString(SIZE(0..255))
    MAX-ACCESS                  read-only
    STATUS                      current
    DESCRIPTION                 "The unique MAC of the Designated Bridge associated with the port's LAN segment."
    ::= { ntronRstpPortsPort 12 }

ntronRstpPortsPortPortDesignatedPort    OBJECT-TYPE
    SYNTAX                      Integer32
    MAX-ACCESS                  read-only
    STATUS                      current
    DESCRIPTION                 "The Designated Port of the Designated Bridge."
    ::= {ntronRstpPortsPort 13}

ntronRstpPortsPortPortNumberId  OBJECT-TYPE
    SYNTAX                      Integer32
    MAX-ACCESS                  read-only
    STATUS                      current
    DESCRIPTION                 "The port number Id."
    ::= {ntronRstpPortsPort 14}

--  ----------------------------------------------------------------------------------
ntronRstpRootBridge   OBJECT IDENTIFIER     ::= {ntronRstpGroup 20}
--  ----------------------------------------------------------------------------------

ntronRstpRootBridgeBridgePriorityStep   OBJECT-TYPE
    SYNTAX                      INTEGER
                                {
                                    priority0       (1),
                                    priority4096    (2),
                                    priority8192    (3),
                                    priority12288   (4),
                                    priority16384   (5),
                                    priority20480   (6),
                                    priority24576   (7),
                                    priority28672   (8),
                                    priority32768   (9),
                                    priority36864   (10),
                                    priority40960   (11),
                                    priority45056   (12),
                                    priority49152   (13),
                                    priority53248   (14),
                                    priority57344   (15),
                                    priority61440   (16)
                                }
    MAX-ACCESS                  read-only
    STATUS                      current
    DESCRIPTION                 "The Priority of the Root Bridge."
    ::= {ntronRstpRootBridge 1}

ntronRstpRootBridgeMacAddress       OBJECT-TYPE
    SYNTAX                      DisplayString(SIZE(0..255))
    MAX-ACCESS                  read-only
    STATUS                      current
    DESCRIPTION                 "The unique MAC of the Root Bridge. Possibly a different network device"
    ::= { ntronRstpRootBridge 2 }

ntronRstpRootBridgeHelloTime        OBJECT-TYPE
    SYNTAX                      Integer32(1..10)
    MAX-ACCESS                  read-only
    STATUS                      current
    DESCRIPTION                 "The time interval, in seconds, between the transmission of Configuration BPDUs by
                                Designated Ports."
    ::= {ntronRstpRootBridge 3}

ntronRstpRootBridgeFowardDelay      OBJECT-TYPE
    SYNTAX                      Integer32(4..30)
    MAX-ACCESS                  read-only
    STATUS                      current
    DESCRIPTION                 "The time spent, in seconds, by legacy STP Bridges in transitioning Root and
                                Designated Ports to Forwarding. This delays Port transitions until other bridges
                                have received spanning tree information."
    ::= {ntronRstpRootBridge 4}

ntronRstpRootBridgeMaxAge   OBJECT-TYPE
    SYNTAX                      Integer32(6..40)
    MAX-ACCESS                  read-only
    STATUS                      current
    DESCRIPTION                 "For RSTP, this is the maximum hops allowed for any protocol message before it is
                                discarded and no longer retransmitted.
                                For STP, this is the maximum time, in seconds, that a bridge will wait for Configuration
                                BPDUs before deciding it is no longer connected to the root bridge."
    ::= {ntronRstpRootBridge 5}

ntronRstpRootBridgePathCost     OBJECT-TYPE
    SYNTAX                      Integer32(0..200000000)
    MAX-ACCESS                  read-only
    STATUS                      current
    DESCRIPTION                 "The cost of the path to the Root Bridge via the Root Port of this bridge."
    ::= { ntronRstpRootBridge 6 }

ntronRstpRootBridgePort OBJECT-TYPE
    SYNTAX                      Integer32
    MAX-ACCESS                  read-only
    STATUS                      current
    DESCRIPTION                 "The Root Port of this Bridge."
    ::= {ntronRstpRootBridge 7}

--  ----------------------------------------------------------------------------------
--
--	VlanGroup
--
--  ----------------------------------------------------------------------------------

--  ----------------------------------------------------------------------------------
ntronVlanConfig   OBJECT IDENTIFIER  	::= {ntronVlanGroup 10}
--  ----------------------------------------------------------------------------------
ntronVlanConfigType				OBJECT-TYPE
   	SYNTAX						INTEGER
								{
									tagged(3)
								}
   	MAX-ACCESS					read-only
   	STATUS						current
   	DESCRIPTION					"VLAN mode of operation."
   	::= { ntronVlanConfig 1 }

ntronVlanConfigIngressReplaceVID	OBJECT-TYPE
    SYNTAX               		INTEGER
								{
									disabled (1),
									enabled  (2)
								}
	MAX-ACCESS   			    read-write
	STATUS              		current
	DESCRIPTION 				"Specifies whether or not to replace the VID tag of ingress frames
								with the port's designated VID (PVID)."
    ::= { ntronVlanConfig 2 }

ntronVlanConfigIngressDiscardUntagged 		OBJECT-TYPE
    SYNTAX     			        DisplayString(SIZE(0..255))
	MAX-ACCESS         			read-write
    STATUS              		current
    DESCRIPTION 				"Specifies ports that drop untagged ingress frames."
    ::= {ntronVlanConfig 3}

	ntronVlanConfigIngressVidFilter 		OBJECT-TYPE
    SYNTAX     			        DisplayString(SIZE(0..255))
	MAX-ACCESS         			read-write
    STATUS              		current
    DESCRIPTION 				"Specifies ports that filter out ingress frames when a VID
								violation is detected."
    ::= {ntronVlanConfig 4}

ntronVlanConfigRemovePortsFromDefaultVlan	OBJECT-TYPE
    SYNTAX               		INTEGER
								{
									disabled (1),
									enabled  (2)
								}
	MAX-ACCESS   			    read-write
	STATUS              		current
	DESCRIPTION 				"Delete ports from default VLAN when adding them to another VLAN"
    ::= { ntronVlanConfig 5 }

ntronVlanConfigPrimaryMgmtVlanId		OBJECT-TYPE
   	SYNTAX						Integer32(1..4094)
   	MAX-ACCESS					read-write
   	STATUS						current
   	DESCRIPTION					"The default egress VLAN used for communications initiated by the switch i.e. DHCP requests."
   	::= { ntronVlanConfig 6 }

ntronTaggedVlansTable     		OBJECT-TYPE
   	SYNTAX    	         		SEQUENCE OF NtronTaggedVlans
	MAX-ACCESS  	        	not-accessible
   	STATUS          	       	current
   	DESCRIPTION  				"VLAN table"
	::= { ntronVlanConfig 7 }

ntronTaggedVlansVlan		  		OBJECT-TYPE
    SYNTAX                		NtronTaggedVlans
    MAX-ACCESS            		not-accessible
    STATUS                		current
    DESCRIPTION					"An entry in the ntronTaggedVlansTable."
	INDEX      					{ ntronTaggedVlansVlanVlanId }
    ::= {ntronTaggedVlansTable 1}

NtronTaggedVlans ::= SEQUENCE {
	ntronTaggedVlansVlanVlanId				Integer32,
	ntronTaggedVlansVlanName				DisplayString,
	ntronTaggedVlansVlanAllowManagement 	INTEGER,
	ntronTaggedVlansVlanUntagEgressPorts 	DisplayString,
	ntronTaggedVlansVlanMemberPorts 		DisplayString
}

ntronTaggedVlansVlanVlanId		OBJECT-TYPE
   	SYNTAX						Integer32(1..4094)
   	MAX-ACCESS					read-write
   	STATUS						current
   	DESCRIPTION					"The VLAN Id."
   	::= { ntronTaggedVlansVlan 1 }

ntronTaggedVlansVlanName 		OBJECT-TYPE
    SYNTAX     			        DisplayString(SIZE(0..255))
	MAX-ACCESS         			read-write
    STATUS              		current
    DESCRIPTION 				"The name of the VLAN."
    ::= {ntronTaggedVlansVlan 2}

ntronTaggedVlansVlanAllowManagement	OBJECT-TYPE
    SYNTAX               		INTEGER
								{
									disabled (1),
									enabled  (2)
								}
	MAX-ACCESS   			    read-write
	STATUS              		current
	DESCRIPTION 				"Specifies whether or not all ports in this VLAN are management ports."
    ::= { ntronTaggedVlansVlan 3 }

ntronTaggedVlansVlanUntagEgressPorts	OBJECT-TYPE
    SYNTAX     			        		DisplayString(SIZE(0..255))
	MAX-ACCESS         					read-write
    STATUS              				current
    DESCRIPTION 						"Specifies ports that untag egress frames."
    ::= {ntronTaggedVlansVlan 4}

ntronTaggedVlansVlanMemberPorts 		OBJECT-TYPE
    SYNTAX     			        DisplayString(SIZE(0..255))
	MAX-ACCESS         			read-write
    STATUS              		current
    DESCRIPTION 				"Ports that are members of the VLAN."
    ::= {ntronTaggedVlansVlan 5}

--  ----------------------------------------------------------------------------------
--
--	SnmpGroup
--
--  ----------------------------------------------------------------------------------

--  ----------------------------------------------------------------------------------
ntronSnmpConfig   OBJECT IDENTIFIER  	::= {ntronSnmpGroup 10}
--  ----------------------------------------------------------------------------------
ntronSnmpConfigStatus		OBJECT-TYPE
    SYNTAX              	INTEGER
							{
								disabled (1),
								enabled  (2)
							}
	MAX-ACCESS   			read-write
	STATUS              	current
	DESCRIPTION 			"Specifies whether or not snmp is enabled/disabled."
    ::= { ntronSnmpConfig 1 }

ntronSnmpConfigEngineIdReset		OBJECT-TYPE
    SYNTAX              	INTEGER
							{
								engineIdResetNo (1),
								engineIdResetYes  (2)
							}
	MAX-ACCESS   			read-write
	STATUS              	current
	DESCRIPTION 			"When the value engineIdResetYes is written the engine ID is
							reset.  A read always returns engineIdResetNo."
    ::= { ntronSnmpConfig 2 }

ntronConfigSnmpTrapDelay	OBJECT-TYPE
    SYNTAX    					Integer32
   	MAX-ACCESS				read-write
   	STATUS					current
   	DESCRIPTION				"Time in seconds to delay before sending out first trap."
    ::= { ntronSnmpConfig 3}

--  ----------------------------------------------------------------------------------
--
--	EventLogGroup
--
--  ----------------------------------------------------------------------------------

--  ----------------------------------------------------------------------------------
ntronEventLogConfig   OBJECT IDENTIFIER  	::= {ntronEventLogGroup 10}
--  ----------------------------------------------------------------------------------
ntronEventLogConfigStatus		OBJECT-TYPE
    SYNTAX              		INTEGER
								{
									disabled (1),
									enabled  (2)
								}
	MAX-ACCESS   				read-write
	STATUS              		current
	DESCRIPTION 				"Specifies whether or not event logging is enabled/disabled."
    ::= { ntronEventLogConfig 1 }

--  ----------------------------------------------------------------------------------
--
--	TimeGroup
--
--  ----------------------------------------------------------------------------------

--  ----------------------------------------------------------------------------------
ntronTimeConfig   OBJECT IDENTIFIER  	::= {ntronTimeGroup 10}
--  ----------------------------------------------------------------------------------
ntronTimeConfigTimeZone 		OBJECT IDENTIFIER ::= { ntronTimeConfig 1}

ntronTimeConfigTimeZoneDescription		OBJECT-TYPE
    SYNTAX     							DisplayString(SIZE(0..255))
	MAX-ACCESS         					read-write
    STATUS              				current
	DESCRIPTION 						"The selected time zone's description."
    ::= { ntronTimeConfigTimeZone 1 }

ntronTimeConfigTimeZoneStandardTimeAbbreviation			OBJECT-TYPE
    SYNTAX     											DisplayString(SIZE(0..11))
	MAX-ACCESS         									read-write
    STATUS              								current
	DESCRIPTION 										"The selected time zone's abbreviation."
    ::= { ntronTimeConfigTimeZone 2 }

ntronTimeConfigTimeZoneDaylightSavingTimeAbbreviation	OBJECT-TYPE
    SYNTAX     											DisplayString(SIZE(0..11))
	MAX-ACCESS         									read-write
    STATUS              								current
	DESCRIPTION 										"The selected time zone's daylight/summer time abbreviation."
    ::= { ntronTimeConfigTimeZone 3 }

ntronTimeConfigTimeZoneUtcOffset		OBJECT-TYPE
    SYNTAX              				Integer32(-720..840)
	MAX-ACCESS   						read-write
	STATUS              				current
	DESCRIPTION 						"The offset, in minutes, from Universal Time Coordinate (UTC). This is used to determine the local time."
    ::= { ntronTimeConfigTimeZone 4 }

ntronTimeConfigDaylightSaving	 		OBJECT IDENTIFIER ::= { ntronTimeConfig 2}

ntronTimeConfigDaylightSavingStatus		OBJECT-TYPE
    SYNTAX              				INTEGER
										{
											disabled (1),
											enabled  (2)
										}
	MAX-ACCESS   						read-write
	STATUS              				current
	DESCRIPTION 						"Specifies whether or not adjusting local time for daylight/summer time is enabled or disabled."
    ::= { ntronTimeConfigDaylightSaving 1 }

ntronTimeConfigDaylightSavingOffset		OBJECT-TYPE
    SYNTAX              				Integer32(-120..120)
	MAX-ACCESS   						read-write
	STATUS              				current
	DESCRIPTION 						"Defines by how many minutes to adjust the time when daylight saving time starts and ends."
    ::= { ntronTimeConfigDaylightSaving 2 }

	ntronTimeConfigDaylightSavingStartMonth	OBJECT-TYPE
    SYNTAX              					INTEGER
											{
												january		(1),
												february	(2),
												march		(3),
												april		(4),
												may			(5),
												june		(6),
												july		(7),
												august		(8),
												september	(9),
												october		(10),
												november	(11),
												december	(12)
											}
	MAX-ACCESS   							read-write
	STATUS              					current
	DESCRIPTION 							"The month when daylight saving time should start."
    ::= { ntronTimeConfigDaylightSaving 3 }

	ntronTimeConfigDaylightSavingStartWeek	OBJECT-TYPE
    SYNTAX              					INTEGER
											{
												first	(1),
												second	(2),
												third	(3),
												fourth	(4),
												last	(5)
											}
	MAX-ACCESS   							read-write
	STATUS              					current
	DESCRIPTION 							"The week when daylight saving time should start."
    ::= { ntronTimeConfigDaylightSaving 4 }

	ntronTimeConfigDaylightSavingStartWeekDay	OBJECT-TYPE
    SYNTAX              						INTEGER
												{
													sunday		(1),
													monday		(2),
													tuesday		(3),
													wednesday	(4),
													thursday	(5),
													friday		(6),
													saturday	(7)
												}
	MAX-ACCESS   								read-write
	STATUS              						current
	DESCRIPTION 								"The day when daylight saving time should start."
    ::= { ntronTimeConfigDaylightSaving 5 }

	ntronTimeConfigDaylightSavingStartHour	OBJECT-TYPE
    SYNTAX              					Integer32(0..23)
	MAX-ACCESS   							read-write
	STATUS              					current
	DESCRIPTION 							"The hour of the day when daylight saving time / summer time should start.
											 For example 0200 hours or 2:00 AM is represented by 2."
    ::= { ntronTimeConfigDaylightSaving 6 }

	ntronTimeConfigDaylightSavingEndMonth	OBJECT-TYPE
    SYNTAX              					INTEGER
											{
												january		(1),
												february	(2),
												march		(3),
												april		(4),
												may			(5),
												june		(6),
												july		(7),
												august		(8),
												september	(9),
												october		(10),
												november	(11),
												december	(12)
											}
	MAX-ACCESS   							read-write
	STATUS              					current
	DESCRIPTION 							"The month when daylight saving time should end."
    ::= { ntronTimeConfigDaylightSaving 7 }

	ntronTimeConfigDaylightSavingEndWeek	OBJECT-TYPE
    SYNTAX              					INTEGER
											{
												first	(1),
												second	(2),
												third	(3),
												fourth	(4),
												last	(5)
											}
	MAX-ACCESS   							read-write
	STATUS              					current
	DESCRIPTION 							"The week when daylight saving time should end."
    ::= { ntronTimeConfigDaylightSaving 8 }

	ntronTimeConfigDaylightSavingEndWeekDay	OBJECT-TYPE
    SYNTAX              					INTEGER
											{
												sunday		(1),
												monday		(2),
												tuesday		(3),
												wednesday	(4),
												thursday	(5),
												friday		(6),
												saturday	(7)
											}
	MAX-ACCESS   								read-write
	STATUS              						current
	DESCRIPTION 								"The day when daylight saving time should end."
    ::= { ntronTimeConfigDaylightSaving 9 }

	ntronTimeConfigDaylightSavingEndHour	OBJECT-TYPE
    SYNTAX              					Integer32(0..23)
	MAX-ACCESS   							read-write
	STATUS              					current
	DESCRIPTION 							"The hour of the day when daylight saving time / summer time should end.
											 For example 0200 hours or 2:00 AM is represented by 2."
    ::= { ntronTimeConfigDaylightSaving 10 }

ntronTimeConfigSystemTime					OBJECT-TYPE
    SYNTAX              					DisplayString(SIZE(0..255))
	MAX-ACCESS   							read-only
	STATUS              					current
	DESCRIPTION 							"Displays the system date and time."
::= { ntronTimeConfig 3  }

ntronTimeConfigTimeSource                   OBJECT-TYPE
    SYNTAX                                  INTEGER
                                            {
                                                manual      (1),
                                                sntp        (2),
                                                ptp         (3)
                                            }
    MAX-ACCESS                              read-write
    STATUS                                  current
    DESCRIPTION                             "This field controls how the switch will automatically set its clock."
::= { ntronTimeConfig 4 }

--  ----------------------------------------------------------------------------------
--
--	TimeSntpGroup
--
--  ----------------------------------------------------------------------------------

--  ----------------------------------------------------------------------------------
ntronTimeSntpConfig   OBJECT IDENTIFIER  	::= {ntronTimeSntpGroup 10}
--  ----------------------------------------------------------------------------------
ntronTimeSntpConfigStatus				OBJECT-TYPE
    SYNTAX              				INTEGER
										{
											disabled (1),
											enabled  (2)
										}
	MAX-ACCESS   						read-write
	STATUS              				current
	DESCRIPTION 						"Specifies whether or not the SNTP client is enabled or disabled. At least one NTP or SNTP server must be configured to enable the SNTP client."
    ::= { ntronTimeSntpConfig 1 }

ntronTimeSntpConfigQueryInterval		OBJECT-TYPE
    SYNTAX              				Integer32(4..129600)
	MAX-ACCESS   						read-write
	STATUS              				current
	DESCRIPTION 						"Time, in seconds, to periodically query the time server."
    ::= { ntronTimeSntpConfig 2 }

ntronTimeSntpConfigTimeServersTable		OBJECT-TYPE
   	SYNTAX    	         				SEQUENCE OF NtronTimeSntpConfigTimeServers
	MAX-ACCESS  	        			not-accessible
   	STATUS          	       			current
   	DESCRIPTION  						"Time Server table"
	::= { ntronTimeSntpConfig 3 }

ntronTimeSntpConfigTimeServer  			OBJECT-TYPE
    SYNTAX                				NtronTimeSntpConfigTimeServers
    MAX-ACCESS            				not-accessible
    STATUS                				current
    DESCRIPTION							"An entry in the ntronTimeSntpConfigTimeServersTable."
	INDEX      							{ ntronTimeSntpConfigTimeServerPriority }
    ::= {ntronTimeSntpConfigTimeServersTable 1}

NtronTimeSntpConfigTimeServers ::= SEQUENCE	{
												ntronTimeSntpConfigTimeServerPriority	Integer32,
												ntronTimeSntpConfigTimeServerAddress	DisplayString
											}

ntronTimeSntpConfigTimeServerPriority	OBJECT-TYPE
   	SYNTAX								Integer32(1..2)
   	MAX-ACCESS							read-write
   	STATUS								current
   	DESCRIPTION							"Priority order of the time server used when querying the time."
   	::= { ntronTimeSntpConfigTimeServer 1 }

ntronTimeSntpConfigTimeServerAddress	OBJECT-TYPE
   	SYNTAX								DisplayString(SIZE(0..255))
   	MAX-ACCESS							read-write
   	STATUS								current
   	DESCRIPTION							"The IP address of the time server."
   	::= { ntronTimeSntpConfigTimeServer 2 }

--  ----------------------------------------------------------------------------------
--
--	SecurityDot1xGroup
--
--  ----------------------------------------------------------------------------------

--  ----------------------------------------------------------------------------------
ntronSecurityDot1xConfig   OBJECT IDENTIFIER  	::= {ntronSecurityDot1xGroup 10}
--  ----------------------------------------------------------------------------------
ntronSecurityDot1xConfigStatus			OBJECT-TYPE
    SYNTAX              				INTEGER
										{
											disabled (1),
											enabled  (2)
										}
	MAX-ACCESS   						read-write
	STATUS              				current
	DESCRIPTION 						"Indicates whether 802.1X is enabled or disabled. At least one RADIUS server
										 must be specified for 802.1X to be enabled. Ports must also be individually
										 enabled on the ports configuration page."
    ::= { ntronSecurityDot1xConfig 1 }

ntronSecurityDot1xConfigEnabledPorts	OBJECT-TYPE
	SYNTAX             					DisplayString(SIZE(0..255))
   	MAX-ACCESS							read-write
   	STATUS								current
   	DESCRIPTION							"Specifies ports that require 802.1x authentication."
   	::= { ntronSecurityDot1xConfig 2}

ntronSecurityDot1xConfigDefaultReauthStatus		OBJECT-TYPE
    SYNTAX              				INTEGER
										{
											disabled (1),
											enabled  (2)
										}
	MAX-ACCESS   						read-write
	STATUS              				current
	DESCRIPTION 						"Indicates whether 802.1X reauthentication is enabled or disabled. With
										 reauthentication enabled, a device will be required to reauthenticate
										 itself based on the time period specified by the reauthentication timeout field.
										 802.1X must be disabled to change this value."
    ::= { ntronSecurityDot1xConfig 3 }

ntronSecurityDot1xConfigDefaultReauthTimeout	OBJECT-TYPE
	SYNTAX             					Integer32
   	MAX-ACCESS							read-write
   	STATUS								current
   	DESCRIPTION							"The time period, in seconds, between 802.1x reauthentication.
										 This value can not be 0. 802.1x must be disabled to change this value."
   	::= { ntronSecurityDot1xConfig 4}

--  ----------------------------------------------------------------------------------
--
--  SecurityRadiusGroup
--
--  ----------------------------------------------------------------------------------

--  ----------------------------------------------------------------------------------
ntronSecurityRadiusConfig   OBJECT IDENTIFIER   ::= {ntronSecurityRadiusGroup 10}
--  ----------------------------------------------------------------------------------
ntronSecurityRadiusConfigServersTable   OBJECT-TYPE
    SYNTAX                              SEQUENCE OF NtronSecurityRadiusConfigServers
    MAX-ACCESS                          not-accessible
    STATUS                              current
    DESCRIPTION                         "RADIUS Server table"
    ::= { ntronSecurityRadiusConfig 1 }

ntronSecurityRadiusConfigServer         OBJECT-TYPE
    SYNTAX                              NtronSecurityRadiusConfigServers
    MAX-ACCESS                          not-accessible
    STATUS                              current
    DESCRIPTION                         "An entry in the ntronSecurityRadiusConfigServersTable."
    INDEX                               { ntronSecurityRadiusConfigServerPriority }
    ::= {ntronSecurityRadiusConfigServersTable 1}

NtronSecurityRadiusConfigServers ::= SEQUENCE   {
                                                    ntronSecurityRadiusConfigServerPriority     Integer32,
                                                    ntronSecurityRadiusConfigServerAddress      DisplayString,
                                                    ntronSecurityRadiusConfigServerAuthPort     Integer32,
                                                    ntronSecurityRadiusConfigServerSharedSecret DisplayString
                                                }

ntronSecurityRadiusConfigServerPriority OBJECT-TYPE
    SYNTAX                              Integer32(1..2)
    MAX-ACCESS                          read-write
    STATUS                              current
    DESCRIPTION                         "Priority order of the RADIUS server used when querying authentication."
    ::= { ntronSecurityRadiusConfigServer 1 }

ntronSecurityRadiusConfigServerAddress  OBJECT-TYPE
    SYNTAX                              DisplayString(SIZE(0..255))
    MAX-ACCESS                          read-write
    STATUS                              current
    DESCRIPTION                         "The IP address of the RADIUS server."
    ::= { ntronSecurityRadiusConfigServer 2 }

ntronSecurityRadiusConfigServerAuthPort OBJECT-TYPE
    SYNTAX                              Integer32(1..65535)
    MAX-ACCESS                          read-write
    STATUS                              current
    DESCRIPTION                         "The UDP port number of the RADIUS Server. The default port number is 1812, per RFC-2865.
                                         Allowed port numbers are 1 - 65535."
    ::= { ntronSecurityRadiusConfigServer 3 }

ntronSecurityRadiusConfigServerSharedSecret OBJECT-TYPE
    SYNTAX                              DisplayString(SIZE(0..255))
    MAX-ACCESS                          read-write
    STATUS                              current
    DESCRIPTION                         "The shared secret authenticates the switch to the RADIUS server
                                         and must match the shared secret value on the RADIUS server. An
                                         empty string will be returned when the object is retrieved."
    ::= { ntronSecurityRadiusConfigServer 4 }

--  ----------------------------------------------------------------------------------
ntronEventLogFilterConfig   OBJECT IDENTIFIER      ::= {ntronEventLogFilterGroup 10}
--  ----------------------------------------------------------------------------------

ntronEventLogFilterConfigFilterTable    OBJECT-TYPE
    SYNTAX                              SEQUENCE OF NtronEventLogFilterConfigFilters
    MAX-ACCESS                          not-accessible
    STATUS                              current
    DESCRIPTION                         "The Event Filter table."
    ::= { ntronEventLogFilterConfig 1 }

ntronEventLogFilterConfigFiltersFilter      OBJECT-TYPE
    SYNTAX                                  NtronEventLogFilterConfigFilters
    MAX-ACCESS                              not-accessible
    STATUS                                  current
    DESCRIPTION                             "An entry in the ntronEventLogFilterConfigFilterTable."
    INDEX                                   { ntronEventLogFilterConfigFiltersFilterComponent }
    ::= { ntronEventLogFilterConfigFilterTable 1 }

NtronEventLogFilterConfigFilters ::= SEQUENCE {
    ntronEventLogFilterConfigFiltersFilterComponent    INTEGER,
    ntronEventLogFilterConfigFiltersFilterSeverity     INTEGER
    }

ntronEventLogFilterConfigFiltersFilterComponent     OBJECT-TYPE
    SYNTAX                                          INTEGER
                                                    {
                                                        dot1x           (1),
                                                        faults          (2),
                                                        nlink           (3),
                                                        nring           (4),
                                                        poe             (5),
                                                        ports           (6),
                                                        radius          (7),
                                                        rstp            (8),
                                                        system          (9),
                                                        time            (10),
                                                        ptp             (11),
                                                        security        (12),
                                                        portSecurity    (13),
                                                        dhcpServer      (14),
                                                        lldp            (15)
                                                    }
    MAX-ACCESS                                      read-only
    STATUS                                          current
    DESCRIPTION                                     "The feature, protocol, or system service of the switch that generated the event. Components not supported in the switch are displayed."
    ::= { ntronEventLogFilterConfigFiltersFilter 1 }

ntronEventLogFilterConfigFiltersFilterSeverity  OBJECT-TYPE
    SYNTAX                                      INTEGER
                                                {
                                                    emergency0      (1),
                                                    alert1          (2),
                                                    critical2       (3),
                                                    error3          (4),
                                                    warning4        (5),
                                                    notice5         (6),
                                                    informational6  (7),
                                                    debug7          (8),
                                                    none            (9)
                                                }
    MAX-ACCESS                                  read-write
    STATUS                                      current
    DESCRIPTION                                 "Events below this severity level will be ignored."
    ::= { ntronEventLogFilterConfigFiltersFilter 2 }

--  ----------------------------------------------------------------------------------
--
--  SyslogGroup
--
--  ----------------------------------------------------------------------------------

--  ----------------------------------------------------------------------------------
ntronSyslogConfig   OBJECT IDENTIFIER       ::= {ntronSyslogGroup 10}
--  ----------------------------------------------------------------------------------

ntronSyslogConfigStatus                 OBJECT-TYPE
    SYNTAX                              INTEGER
                                        {
                                            disabled (1),
                                            enabled  (2)
                                        }
    MAX-ACCESS                          read-write
    STATUS                              current
    DESCRIPTION                         "This field indicates whether the Syslog Distributor (client) has been enabled or disabled. To enable Syslog at least
                                         one Syslog Collector (server) must be specified."
    ::= { ntronSyslogConfig 1 }

ntronSyslogConfigFacility               OBJECT-TYPE
    SYNTAX                              INTEGER
                                        {
                                            userLevel (1),
                                            localUse0 (16),
                                            localUse1 (17),
                                            localUse2 (18),
                                            localUse3 (19),
                                            localIse4 (20),
                                            localUse5 (21),
                                            localUse6 (22),
                                            localUse7 (23)
                                        }
    MAX-ACCESS                          read-write
    STATUS                              current
    DESCRIPTION                         "This is used to identify which process is logging the message. This is a global setting for the switch and will be used
                                         for all messages. Available Facility values as defined per RFC-3164 are 1 (user level) and 16 - 23 (local use)."
    ::= { ntronSyslogConfig 2 }

ntronSyslogConfigOriginatorIpAddress    OBJECT-TYPE
    SYNTAX                              IpAddress
    MAX-ACCESS                          read-only
    STATUS                              current
    DESCRIPTION                         "This field displays the configured IP address of the switch."
    ::= { ntronSyslogConfig 3 }

ntronSyslogConfigCollectorsTable        OBJECT-TYPE
    SYNTAX                              SEQUENCE OF NtronSyslogConfigCollectors
    MAX-ACCESS                          not-accessible
    STATUS                              current
    DESCRIPTION                         "The table of Syslog servers to which the messages are sent."
    ::= { ntronSyslogConfig 4 }

ntronSyslogConfigCollector              OBJECT-TYPE
    SYNTAX                              NtronSyslogConfigCollectors
    MAX-ACCESS                          not-accessible
    STATUS                              current
    DESCRIPTION                         "An entry in the ntronSyslogConfigCollectorsTable."
    INDEX                               { ntronSyslogConfigCollectorId }
    ::= {ntronSyslogConfigCollectorsTable 1}

NtronSyslogConfigCollectors ::= SEQUENCE    {
                                                ntronSyslogConfigCollectorIpAddress     IpAddress,
                                                ntronSyslogConfigCollectorUdpPortNumber Integer32,
                                                ntronSyslogConfigCollectorMinSeverity   INTEGER,
                                                ntronSyslogConfigCollectorSendEvents    INTEGER,
                                                ntronSyslogConfigCollectorId            Integer32
                                            }

ntronSyslogConfigCollectorIpAddress     OBJECT-TYPE
    SYNTAX                              IpAddress
    MAX-ACCESS                          read-write
    STATUS                              current
    DESCRIPTION                         "The IP address of the Collector (server) to receive a log message."
    ::= { ntronSyslogConfigCollector 1 }

ntronSyslogConfigCollectorUdpPortNumber OBJECT-TYPE
    SYNTAX                              Integer32(1..65535)
    MAX-ACCESS                          read-write
    STATUS                              current
    DESCRIPTION                         "The UDP port on the Collector (server) configured to receive the message. The default port number is 514, per RFC-3164, but can be changed to meet installation requirements.
                                         Allowed port numbers are 1 - 65535."
    ::= { ntronSyslogConfigCollector 2 }

ntronSyslogConfigCollectorMinSeverity   OBJECT-TYPE
    SYNTAX                                  INTEGER
                                            {
                                                emergency0      (1),
                                                alert1          (2),
                                                critical2       (3),
                                                error3          (4),
                                                warning4        (5),
                                                notice5         (6),
                                                informational6  (7),
                                                debug7          (8)
                                            }
    MAX-ACCESS                              read-write
    STATUS                                  current
    DESCRIPTION                             "The minimum Severity level of the messages that will be sent to the specified Collector (server). Values range from Debug (7) to Emergency (0). For example, a Collector
                                             configured with a value of Warning (4) will receive all messages from 4 to 0. The importance of a message increases with a lower severity level setting value.
                                             These are the same Severity level setting values as the Event Log and Event Log Filter. For more information, see Severity under section 2.5 Event Log."
    ::= { ntronSyslogConfigCollector 3 }

    ntronSyslogConfigCollectorSendEvents    OBJECT-TYPE
    SYNTAX                                      INTEGER
                                                {
                                                    no  (1),
                                                    yes (2)
                                                }
    MAX-ACCESS                                  read-write
    STATUS                                      current
    DESCRIPTION                                 "This setting can be enabled or disabled, per Collector, to control the distribution of Event Log messages."
    ::= { ntronSyslogConfigCollector 4 }

    ntronSyslogConfigCollectorId        OBJECT-TYPE
    SYNTAX                                  Integer32
    MAX-ACCESS                              read-only
    STATUS                                  current
    DESCRIPTION                             "Collector Id number."
    ::= { ntronSyslogConfigCollector 5 }

--  ----------------------------------------------------------------------------------
--
--  LocalSecurityGroup
--
--  ----------------------------------------------------------------------------------

--  ----------------------------------------------------------------------------------
ntronLocalSecurityConfig   OBJECT IDENTIFIER       ::= {ntronLocalSecurityGroup 10}
--  ----------------------------------------------------------------------------------
ntronLocalAccessConfig                      OBJECT IDENTIFIER ::= {ntronLocalSecurityConfig 1}
ntronLocalAccessAuthenticationConfig        OBJECT IDENTIFIER ::= {ntronLocalSecurityConfig 2}
ntronCertificateKeyConfig                   OBJECT IDENTIFIER ::= {ntronLocalSecurityConfig 3}

ntronLocalAccessConfigTelnetServerStatus    OBJECT-TYPE
    SYNTAX                                  INTEGER
                                            {
                                                disabled    (1),
                                                enabled     (2)
                                            }
    MAX-ACCESS                              read-write
    STATUS                                  current
    DESCRIPTION                             "This field indicates whether the Telnet Server is enabled or disabled. Disabling the Telnet
                                            Server does not impact SSH. The default is disabled."
    ::= { ntronLocalAccessConfig 1 }

ntronLocalAccessConfigSshServerStatus    OBJECT-TYPE
    SYNTAX                                  INTEGER
                                            {
                                                disabled    (1),
                                                enabled     (2)
                                            }
    MAX-ACCESS                              read-write
    STATUS                                  current
    DESCRIPTION                             "This field indicates whether the SSH Server is enabled or disabled. Disabling the SSH
                                            Server does not impact Telnet. The default is enabled."
    ::= { ntronLocalAccessConfig 2 }

ntronLocalAccessConfigHTTPStatus        OBJECT-TYPE
    SYNTAX                              INTEGER
                                        {
                                            disabled    (1),
                                            enabled     (2)
                                        }
    MAX-ACCESS                          read-write
    STATUS                              current
    DESCRIPTION                         "This field indicates whether HTTP is enabled or disabled. HTTP users are not authenticated by the RADIUS server.
                                        If RADIUS authentication is exclusively required,then please disable HTTP. Disabling HTTP requires HTTPS to be enabled.
                                        The default is disabled."
    ::= { ntronLocalAccessConfig 3 }

ntronLocalAccessConfigHTTPSStatus       OBJECT-TYPE
    SYNTAX                              INTEGER
                                        {
                                            disabled    (1),
                                            enabled     (2)
                                        }
    MAX-ACCESS                          read-write
    STATUS                              current
    DESCRIPTION                         "This field indicates whether HTTPS is enabled or disabled. Disabling HTTPS requires HTTP to be enabled.
                                        The default is enabled."
    ::= { ntronLocalAccessConfig 4 }

ntronLocalAccessConfigConfigDevStatus   OBJECT-TYPE
    SYNTAX                              INTEGER
                                        {
                                            disabled    (1),
                                            enabled     (2)
                                        }
    MAX-ACCESS                          read-write
    STATUS                              current
    DESCRIPTION                         "This field indicates whether the Configuration Device is enabled or disabled. The default is enabled."
    ::= { ntronLocalAccessConfig 5 }

ntronLocalAccessAuthenticationConfigRadiusStatus    OBJECT-TYPE
    SYNTAX                                          INTEGER
                                                    {
                                                        disabled    (1),
                                                        enabled     (2)
                                                    }
    MAX-ACCESS                                      read-write
    STATUS                                          current
    DESCRIPTION                                     "This field indicates whether RADIUS Local Access Authentication is enabled or disabled.
                                                    RADIUS authentication is not supported on HTTP connections. The default is disabled."
    ::= { ntronLocalAccessAuthenticationConfig 1 }

ntronLocalAccessAuthenticationConfigServerAddress   OBJECT-TYPE
    SYNTAX                                          IpAddress
    MAX-ACCESS                                      read-write
    STATUS                                          current
    DESCRIPTION                                     "The IP address of the RADIUS server used when RADIUS Local Access Authentication is enabled."
    ::= { ntronLocalAccessAuthenticationConfig 2 }

ntronLocalAccessAuthenticationConfigServerAuthPort  OBJECT-TYPE
    SYNTAX                                          Integer32(1..65535)
    MAX-ACCESS                                      read-write
    STATUS                                          current
    DESCRIPTION                                     "The UDP port number on the RADIUS server."
    ::= { ntronLocalAccessAuthenticationConfig 3 }

ntronLocalAccessAuthenticationConfigServerSharedSecret  OBJECT-TYPE
    SYNTAX                                              DisplayString(SIZE(0..255))
    MAX-ACCESS                                          read-write
    STATUS                                              current
    DESCRIPTION                                         "The shared secret for the local access authentication server. The shared secret authenticates the switch
                                                        to the RADIUS server and must match the shared secret value on the RADIUS server. An empty string will be
                                                        returned when the object is retrieved."
    ::= { ntronLocalAccessAuthenticationConfig 4 }

ntronCertificateKeyConfigGenerateAtBootUp           OBJECT-TYPE
    SYNTAX                                          INTEGER
                                                    {
                                                        no    (1),
                                                        yes   (2)
                                                    }
    MAX-ACCESS                                      read-write
    STATUS                                          current
    DESCRIPTION                                     "This field indicates whether certificate and keys will be generated when the switch boots up.
                                                    A change to this setting requires settings to be saved and a reboot to take effect. The value
                                                    will reset to no when the switch boots up. The default is no."
    ::= { ntronCertificateKeyConfig 1 }

    --  ----------------------------------------------------------------------------------
--
--  PortSecurityGroup
--
--  ----------------------------------------------------------------------------------

--  ----------------------------------------------------------------------------------
ntronPortSecurityConfig   OBJECT IDENTIFIER       ::= {ntronPortSecurityGroup 10}
--  ----------------------------------------------------------------------------------

ntronPortSecurityConfigStatus    OBJECT-TYPE
    SYNTAX                                  INTEGER
                                            {
                                                disabled    (1),
                                                learning    (2),
                                                locked      (3)
                                            }
    MAX-ACCESS                              read-write
    STATUS                                  current
    DESCRIPTION                             "The current status of Port Security. It can be Disabled, Learning, or Locked.
                                            Transitioning from Locked to Learning clears the Authorization List table on all ports.
                                            Transitioning from Locked to Disabled retains the current Authorization List.
                                            When transitioning from Learning to Locked, the Authorization List represents the authorized MAC addresses.
                                            The default value is Disabled."
    ::= { ntronPortSecurityConfig  1 }

ntronPortSecurityConfigPortsTable   OBJECT-TYPE
    SYNTAX                          SEQUENCE OF NtronPortSecurityConfigPorts
    MAX-ACCESS                      not-accessible
    STATUS                          current
    DESCRIPTION                     ""
    ::= { ntronPortSecurityConfig 2}

ntronPortSecurityConfigPortsPort            OBJECT-TYPE
    SYNTAX                                  NtronPortSecurityConfigPorts
    MAX-ACCESS                              not-accessible
    STATUS                                  current
    DESCRIPTION                             "An entry in the ntronPortSecurityConfigPortsTable."
    INDEX                                   { ntronPortSecurityConfigPortsPortNumberId }
    ::= { ntronPortSecurityConfigPortsTable 1 }

NtronPortSecurityConfigPorts ::= SEQUENCE {
    ntronPortSecurityConfigPortsPortPortId              DisplayString,
    ntronPortSecurityConfigPortsPortSecurePortStatus    INTEGER,
    ntronPortSecurityConfigPortsPortNumberId            Integer32
}

ntronPortSecurityConfigPortsPortPortId  OBJECT-TYPE
    SYNTAX                              DisplayString(SIZE(0..255))
    MAX-ACCESS                          read-only
    STATUS                              current
    DESCRIPTION                         "The descriptive name of the port."
    ::= { ntronPortSecurityConfigPortsPort 1}

ntronPortSecurityConfigPortsPortSecurePortStatus    OBJECT-TYPE
    SYNTAX                                          INTEGER
                                                    {
                                                        disabled    (1),
                                                        enabled     (2),
                                                        singleMAC   (3)
                                                    }
    MAX-ACCESS                                      read-write
    STATUS                                          current
    DESCRIPTION                                     "Displays Secure mode for the associated port. It can be Disabled, Enabled, or Single Mac.
                                                     Disabled: Port Security is not active on the port regardless of the current Port Security Status.
                                                     Enabled: Port Security is active when the current Port Security Status is Learning or Locked.
                                                     Single MAC: Port Security will take the first learned MAC address and lock the port when current
                                                     Port Security Status is Learning or Locked.
                                                     The default value is Disabled."
    ::= { ntronPortSecurityConfigPortsPort 2}

ntronPortSecurityConfigPortsPortNumberId    OBJECT-TYPE
    SYNTAX                                  Integer32
    MAX-ACCESS                              read-only
    STATUS                                  current
    DESCRIPTION                             "The port number Id."
    ::= { ntronPortSecurityConfigPortsPort 3}

--  ----------------------------------------------------------------------------------
--
--  DhcpsGroup
--
--  ----------------------------------------------------------------------------------

--  ----------------------------------------------------------------------------------
ntronDhcpsConfig   OBJECT IDENTIFIER       ::= {ntronDhcpsGroup 10}
--  ----------------------------------------------------------------------------------

ntronDhcpsConfigStatus                      OBJECT-TYPE
    SYNTAX                                  INTEGER
                                            {
                                                disabled    (1),
                                                enabled     (2)
                                            }
    MAX-ACCESS                              read-write
    STATUS                                  current
    DESCRIPTION                             "Indicates whether the DHCP server is active. The default is disabled."
    ::= { ntronDhcpsConfig 1}

ntronDhcpsConfigAcceptBroadcastRequests     OBJECT-TYPE
    SYNTAX                                  INTEGER
                                            {
                                                disabled    (1),
                                                enabled     (2)
                                            }
    MAX-ACCESS                              read-write
    STATUS                                  current
    DESCRIPTION                             "Indicates whether the DHCP server will process broadcast messages.
                                             Typically, client requests are broadcast and relay agent requests are unicast.
                                             When enabled, the server will respond to broadcast requests. When disabled, the
                                             server will ignore broadcast requests. The default is enabled."
    ::= { ntronDhcpsConfig 2 }

ntronDhcpsConfigDelayBroadcastResponsesMs   OBJECT-TYPE
    SYNTAX                                  Integer32(0..2500)
    MAX-ACCESS                              read-write
    STATUS                                  current
    DESCRIPTION                             "The amount of time (in milliseconds) that the DHCP server will delay the processing
                                             of a broadcast message. This setting is used when clients and relay agents are on the
                                             same subnet and/or VLAN. A delay provides the opportunity for relay agent requests to
                                             be honored before client requests. This setting only applies when ntronDhcpsConfigAcceptBroadcastRequests
                                             is enabled. The range is 0-2500 and the default is 500."
    ::= { ntronDhcpsConfig 3 }

ntronDhcpsConfigScopesTable                                      OBJECT-TYPE
    SYNTAX                                                       SEQUENCE OF NtronDhcpsConfigScopes
    MAX-ACCESS                                                   not-accessible
    STATUS                                                       current
    DESCRIPTION                                                  "Table of ntronDhcpsConfigScopesScope entries."
    ::= { ntronDhcpsConfig 4}

ntronDhcpsConfigScopesScope                                      OBJECT-TYPE
    SYNTAX                                                       NtronDhcpsConfigScopes
    MAX-ACCESS                                                   not-accessible
    STATUS                                                       current
    DESCRIPTION                                                  "An entry in the ntronDhcpsConfigScopesTable."
    INDEX                                                        { ntronDhcpsConfigScopesScopeIndex }
    ::= { ntronDhcpsConfigScopesTable 1 }

NtronDhcpsConfigScopes ::= SEQUENCE {
    ntronDhcpsConfigScopesScopeIndex                                    Integer32,
    ntronDhcpsConfigScopesScopeEnable                                   INTEGER,
    ntronDhcpsConfigScopesScopePoolName                                 DisplayString,
    ntronDhcpsConfigScopesScopeLowIp                                    IpAddress,
    ntronDhcpsConfigScopesScopeHighIp                                   IpAddress,
    ntronDhcpsConfigScopesScopeGateway                                  IpAddress,
    ntronDhcpsConfigScopesScopeDomain                                   DisplayString,
    ntronDhcpsConfigScopesScopeDns1                                     IpAddress,
    ntronDhcpsConfigScopesScopeDns2                                     IpAddress,
    ntronDhcpsConfigScopesScopeLeaseDays                                Integer32,
    ntronDhcpsConfigScopesScopeLeaseHours                               Integer32,
    ntronDhcpsConfigScopesScopeLeaseMinutes                             Integer32,
    ntronDhcpsConfigScopesScopeLeaseForever                             INTEGER,
    ntronDhcpsConfigScopesScopeSubnetMask                               IpAddress
}

ntronDhcpsConfigScopesScopeIndex                                OBJECT-TYPE
    SYNTAX                                                      Integer32
    MAX-ACCESS                                                  read-only
    STATUS                                                      current
    DESCRIPTION                                                 "The index of the ntronDhcpsConfigScopesScope entry."
    ::= { ntronDhcpsConfigScopesScope 1}

ntronDhcpsConfigScopesScopeEnable                               OBJECT-TYPE
    SYNTAX                                                      INTEGER
                                                                {
                                                                    false    (1),
                                                                    true     (2)
                                                                }
    MAX-ACCESS                                                  read-write
    STATUS                                                      current
    DESCRIPTION                                                 "Indicates whether the pool is enabled or disabled."
    ::= { ntronDhcpsConfigScopesScope 2}

ntronDhcpsConfigScopesScopePoolName                             OBJECT-TYPE
    SYNTAX                                                      DisplayString(SIZE(0..20))
    MAX-ACCESS                                                  read-write
    STATUS                                                      current
    DESCRIPTION                                                 "Descriptive name of the scope configuration pool. This field
                                                                 is required and must be unique."
    ::= { ntronDhcpsConfigScopesScope 3}

ntronDhcpsConfigScopesScopeLowIp                                OBJECT-TYPE
    SYNTAX                                                      IpAddress
    MAX-ACCESS                                                  read-write
    STATUS                                                      current
    DESCRIPTION                                                 "Starting IP address for the pool of addresses."
    ::= { ntronDhcpsConfigScopesScope 4}

ntronDhcpsConfigScopesScopeHighIp                               OBJECT-TYPE
    SYNTAX                                                      IpAddress
    MAX-ACCESS                                                  read-write
    STATUS                                                      current
    DESCRIPTION                                                 "Ending IP address for the pool of addresses."
    ::= { ntronDhcpsConfigScopesScope 5}

ntronDhcpsConfigScopesScopeGateway                              OBJECT-TYPE
    SYNTAX                                                      IpAddress
    MAX-ACCESS                                                  read-write
    STATUS                                                      current
    DESCRIPTION                                                 "The gateway IP address offered to the client. This field is optional."
    ::= { ntronDhcpsConfigScopesScope 6}

ntronDhcpsConfigScopesScopeDomain                               OBJECT-TYPE
    SYNTAX                                                      DisplayString(SIZE(0..255))
    MAX-ACCESS                                                  read-write
    STATUS                                                      current
    DESCRIPTION                                                 "The domain name offered to the client. This field is optional."
    ::= { ntronDhcpsConfigScopesScope 7}

ntronDhcpsConfigScopesScopeDns1                                 OBJECT-TYPE
    SYNTAX                                                      IpAddress
    MAX-ACCESS                                                  read-write
    STATUS                                                      current
    DESCRIPTION                                                 "A DNS server IP address offered to the client. This field is optional."
    ::= { ntronDhcpsConfigScopesScope 8}

ntronDhcpsConfigScopesScopeDns2                                 OBJECT-TYPE
    SYNTAX                                                      IpAddress
    MAX-ACCESS                                                  read-write
    STATUS                                                      current
    DESCRIPTION                                                 "A DNS server IP address offered to the client. This field is optional."
    ::= { ntronDhcpsConfigScopesScope 9}

ntronDhcpsConfigScopesScopeLeaseDays                            OBJECT-TYPE
    SYNTAX                                                      Integer32(0..1000)
    MAX-ACCESS                                                  read-write
    STATUS                                                      current
    DESCRIPTION                                                 "The lease time in days that will be offered to the client. The range is 0 to 1000 days.
                                                                 The combined time of ntronDhcpsConfigScopesScopeLeaseDays, ntronDhcpsConfigScopesScopeLeaseHours,
                                                                 and ntronDhcpsConfigScopesScopeLeaseMinutes ranges from 1 minute to 1000 days. The combined default
                                                                 is 28 days. Note that if ntronDhcpsConfigScopesScopeLeaseForever is true, the lease does not expire
                                                                 and this configuration will be ignored."
    ::= { ntronDhcpsConfigScopesScope 10}

ntronDhcpsConfigScopesScopeLeaseHours                           OBJECT-TYPE
    SYNTAX                                                      Integer32(0..23)
    MAX-ACCESS                                                  read-write
    STATUS                                                      current
    DESCRIPTION                                                 "The lease time in hours that will be offered to the client. The range is 0 to 23 hours.
                                                                 The combined time of ntronDhcpsConfigScopesScopeLeaseDays, ntronDhcpsConfigScopesScopeLeaseHours,
                                                                 and ntronDhcpsConfigScopesScopeLeaseMinutes ranges from 1 minute to 1000 days. The combined default
                                                                 is 28 days.Note that if ntronDhcpsConfigScopesScopeLeaseForever is true, the lease does not expire
                                                                 and this configuration will be ignored."
    ::= { ntronDhcpsConfigScopesScope 11}

ntronDhcpsConfigScopesScopeLeaseMinutes                         OBJECT-TYPE
    SYNTAX                                                      Integer32(0..59)
    MAX-ACCESS                                                  read-write
    STATUS                                                      current
    DESCRIPTION                                                 "The lease time in minutes that will be offered to the client. The range is 0 to 59 minutes.
                                                                 The combined time of ntronDhcpsConfigScopesScopeLeaseDays, ntronDhcpsConfigScopesScopeLeaseHours,
                                                                 and ntronDhcpsConfigScopesScopeLeaseMinutes ranges from 1 minute to 1000 days. The combined default
                                                                 is 28 days.Note that if ntronDhcpsConfigScopesScopeLeaseForever is true, the lease does not expire
                                                                 and this configuration will be ignored."
    ::= { ntronDhcpsConfigScopesScope 12}

ntronDhcpsConfigScopesScopeLeaseForever                         OBJECT-TYPE
    SYNTAX                                                      INTEGER
                                                                {
                                                                    disabled    (1),
                                                                    enabled     (2)
                                                                }
    MAX-ACCESS                                                  read-write
    STATUS                                                      current
    DESCRIPTION                                                 "If set to enabled, the lease does not expire. Note that if enabled, ntronDhcpsConfigScopesScopeLeaseDays,
                                                                 ntronDhcpsConfigScopesScopeLeaseHours, and ntronDhcpsConfigScopesScopeLeaseMinutes will be ignored."
    ::= { ntronDhcpsConfigScopesScope 13}

ntronDhcpsConfigScopesScopeSubnetMask                           OBJECT-TYPE
    SYNTAX                                                      IpAddress
    MAX-ACCESS                                                  read-write
    STATUS                                                      current
    DESCRIPTION                                                 "The subnet mask for the IP address pool."
    ::= { ntronDhcpsConfigScopesScope 14}

ntronDhcpsConfigStaticAssignmentsTable                          OBJECT-TYPE
    SYNTAX                                                      SEQUENCE OF NtronDhcpsConfigStaticAssignments
    MAX-ACCESS                                                  not-accessible
    STATUS                                                      current
    DESCRIPTION                                                 "Table of ntronDhcpsConfigStaticAssignmentsStaticAssignment entries."
    ::= { ntronDhcpsConfig 5}

ntronDhcpsConfigStaticAssignmentsStaticAssignment            OBJECT-TYPE
    SYNTAX                                                   NtronDhcpsConfigStaticAssignments
    MAX-ACCESS                                               not-accessible
    STATUS                                                   current
    DESCRIPTION                                              "An entry in the ntronDhcpsConfigStaticAssignmentsTable."
    INDEX                                                    { ntronDhcpsConfigStaticAssignmentsStaticAssignmentId }
    ::= { ntronDhcpsConfigStaticAssignmentsTable 1 }

NtronDhcpsConfigStaticAssignments ::= SEQUENCE {
    ntronDhcpsConfigStaticAssignmentsStaticAssignmentId                 Integer32,
    ntronDhcpsConfigStaticAssignmentsStaticAssignmentPoolName           DisplayString,
    ntronDhcpsConfigStaticAssignmentsStaticAssignmentDhcpOption         INTEGER,
    ntronDhcpsConfigStaticAssignmentsStaticAssignmentIpAddress          IpAddress,
    ntronDhcpsConfigStaticAssignmentsStaticAssignmentClientFormat       INTEGER,
    ntronDhcpsConfigStaticAssignmentsStaticAssignmentClientId           DisplayString,
    ntronDhcpsConfigStaticAssignmentsStaticAssignmentRemoteAgentFormat  INTEGER,
    ntronDhcpsConfigStaticAssignmentsStaticAssignmentRemoteAgentId      DisplayString,
    ntronDhcpsConfigStaticAssignmentsStaticAssignmentCircuitFormat      INTEGER,
    ntronDhcpsConfigStaticAssignmentsStaticAssignmentCircuitId          DisplayString,
    ntronDhcpsConfigStaticAssignmentsStaticAssignmentLabel              DisplayString
}

ntronDhcpsConfigStaticAssignmentsStaticAssignmentId             OBJECT-TYPE
    SYNTAX                                                      Integer32
    MAX-ACCESS                                                  read-only
    STATUS                                                      current
    DESCRIPTION                                                 "The index of the ntronDhcpsConfigStaticAssignmentsStaticAssignment entry."
    ::= { ntronDhcpsConfigStaticAssignmentsStaticAssignment 1}

ntronDhcpsConfigStaticAssignmentsStaticAssignmentPoolName       OBJECT-TYPE
    SYNTAX                                                      DisplayString(SIZE(0..20))
    MAX-ACCESS                                                  read-write
    STATUS                                                      current
    DESCRIPTION                                                 "Descriptive name of the scope configuration pool."
    ::= { ntronDhcpsConfigStaticAssignmentsStaticAssignment 2}

ntronDhcpsConfigStaticAssignmentsStaticAssignmentDhcpOption     OBJECT-TYPE
    SYNTAX                                                      INTEGER
                                                                {
                                                                    option61    (1),
                                                                    option82    (2)
                                                                }
    MAX-ACCESS                                                  read-write
    STATUS                                                      current
    DESCRIPTION                                                 "The type of binding identifier for the static assignment. The options are option61 and option82."
    ::= { ntronDhcpsConfigStaticAssignmentsStaticAssignment 3}

ntronDhcpsConfigStaticAssignmentsStaticAssignmentIpAddress      OBJECT-TYPE
    SYNTAX                                                      IpAddress
    MAX-ACCESS                                                  read-write
    STATUS                                                      current
    DESCRIPTION                                                 "The static IP address offered to the DHCP client."
    ::= { ntronDhcpsConfigStaticAssignmentsStaticAssignment 4}

ntronDhcpsConfigStaticAssignmentsStaticAssignmentClientFormat   OBJECT-TYPE
    SYNTAX                                                      INTEGER
                                                                {
                                                                    mac         (1),
                                                                    hex         (2),
                                                                    string      (3)
                                                                }
    MAX-ACCESS                                                  read-write
    STATUS                                                      current
    DESCRIPTION                                                 "The format type of the client. The options are mac, hex, and string. Note, this configuration is only
                                                                 valid when option61 is set in ntronDhcpsConfigStaticAssignmentsStaticAssignmentDhcpOption and will be ignored
                                                                 otherwise."
    ::= { ntronDhcpsConfigStaticAssignmentsStaticAssignment 5}

ntronDhcpsConfigStaticAssignmentsStaticAssignmentClientId       OBJECT-TYPE
    SYNTAX                                                      DisplayString(SIZE(0..255))
    MAX-ACCESS                                                  read-write
    STATUS                                                      current
    DESCRIPTION                                                 "The actual value of the client. This configuration is only valid when option61
                                                                 is set in ntronDhcpsConfigStaticAssignmentsStaticAssignmentDhcpOption and will be ignored
                                                                 otherwise."
    ::= { ntronDhcpsConfigStaticAssignmentsStaticAssignment 6}

ntronDhcpsConfigStaticAssignmentsStaticAssignmentRemoteAgentFormat   OBJECT-TYPE
    SYNTAX                                                               INTEGER
                                                                         {
                                                                            ip          (1),
                                                                            mac         (2),
                                                                            hex         (3),
                                                                            string      (4)
                                                                         }
    MAX-ACCESS                                                           read-write
    STATUS                                                               current
    DESCRIPTION                                                          "The format type of the remote agent. The options are ip, mac, hex, and string. Note, this configuration is only
                                                                          valid when option 82 is set in ntronDhcpsConfigStaticAssignmentsStaticAssignmentDhcpOption and will be ignored
                                                                          otherwise."
    ::= { ntronDhcpsConfigStaticAssignmentsStaticAssignment 7}

ntronDhcpsConfigStaticAssignmentsStaticAssignmentRemoteAgentId       OBJECT-TYPE
    SYNTAX                                                           DisplayString(SIZE(0..52))
    MAX-ACCESS                                                       read-write
    STATUS                                                           current
    DESCRIPTION                                                      "The actual value of the remote agent. This configuration is only valid when option82
                                                                      is set in ntronDhcpsConfigStaticAssignmentsStaticAssignmentDhcpOption and will be ignored
                                                                      otherwise."
    ::= { ntronDhcpsConfigStaticAssignmentsStaticAssignment 8}

    ntronDhcpsConfigStaticAssignmentsStaticAssignmentCircuitFormat   OBJECT-TYPE
    SYNTAX                                                           INTEGER
                                                                     {
                                                                         mac         (1),
                                                                         hex         (2),
                                                                         string      (3)
                                                                     }
    MAX-ACCESS                                                       read-write
    STATUS                                                           current
    DESCRIPTION                                                      "The actual value of the circuit. This configuration is only valid when option82
                                                                      is set in ntronDhcpsConfigStaticAssignmentsStaticAssignmentDhcpOption and will be ignored
                                                                      otherwise."
    ::= { ntronDhcpsConfigStaticAssignmentsStaticAssignment 9}

ntronDhcpsConfigStaticAssignmentsStaticAssignmentCircuitId       OBJECT-TYPE
    SYNTAX                                                       DisplayString(SIZE(0..52))
    MAX-ACCESS                                                   read-write
    STATUS                                                       current
    DESCRIPTION                                                  "The actual value of the circuit. This configuration is only valid when option82
                                                                  is set in ntronDhcpsConfigStaticAssignmentsStaticAssignmentDhcpOption and will be ignored
                                                                  otherwise."
    ::= { ntronDhcpsConfigStaticAssignmentsStaticAssignment 10}

ntronDhcpsConfigStaticAssignmentsStaticAssignmentLabel           OBJECT-TYPE
    SYNTAX                                                       DisplayString(SIZE(0..32))
    MAX-ACCESS                                                   read-write
    STATUS                                                       current
    DESCRIPTION                                                  "The descriptive name of the static assignment. The field is optional."
    ::= { ntronDhcpsConfigStaticAssignmentsStaticAssignment 11}

ntronDhcpsConfigStaticPortAssignmentsTable                      OBJECT-TYPE
    SYNTAX                                                      SEQUENCE OF NtronDhcpsConfigStaticPortAssignments
    MAX-ACCESS                                                  not-accessible
    STATUS                                                      current
    DESCRIPTION                                                 "Table of ntronDhcpsConfigStaticPortAssignmentsStaticPortAssignment entries."
    ::= { ntronDhcpsConfig 6}

ntronDhcpsConfigStaticPortAssignmentsStaticPortAssignment    OBJECT-TYPE
    SYNTAX                                                   NtronDhcpsConfigStaticPortAssignments
    MAX-ACCESS                                               not-accessible
    STATUS                                                   current
    DESCRIPTION                                              "An entry in the ntronDhcpsConfigStaticPortAssignmentsTable."
    INDEX                                                    { ntronDhcpsConfigStaticPortAssignmentsStaticPortAssignmentPortNumberId }
    ::= { ntronDhcpsConfigStaticPortAssignmentsTable 1 }

NtronDhcpsConfigStaticPortAssignments ::= SEQUENCE {
    ntronDhcpsConfigStaticPortAssignmentsStaticPortAssignmentPortNumber     DisplayString,
    ntronDhcpsConfigStaticPortAssignmentsStaticPortAssignmentEnable         INTEGER,
    ntronDhcpsConfigStaticPortAssignmentsStaticPortAssignmentIpAddress      IpAddress,
    ntronDhcpsConfigStaticPortAssignmentsStaticPortAssignmentSubnetMask     IpAddress,
    ntronDhcpsConfigStaticPortAssignmentsStaticPortAssignmentGateway        IpAddress,
    ntronDhcpsConfigStaticPortAssignmentsStaticPortAssignmentDomain         DisplayString,
    ntronDhcpsConfigStaticPortAssignmentsStaticPortAssignmentDnsOne         IpAddress,
    ntronDhcpsConfigStaticPortAssignmentsStaticPortAssignmentDnsTwo         IpAddress,
    ntronDhcpsConfigStaticPortAssignmentsStaticPortAssignmentLabel          DisplayString,
    ntronDhcpsConfigStaticPortAssignmentsStaticPortAssignmentPortNumberId   Integer32
}

ntronDhcpsConfigStaticPortAssignmentsStaticPortAssignmentPortNumber     OBJECT-TYPE
    SYNTAX                                                              DisplayString(SIZE(0..255))
    MAX-ACCESS                                                          read-only
    STATUS                                                              current
    DESCRIPTION                                                         "The descriptive name of the port."
    ::= { ntronDhcpsConfigStaticPortAssignmentsStaticPortAssignment 1}

ntronDhcpsConfigStaticPortAssignmentsStaticPortAssignmentEnable         OBJECT-TYPE
    SYNTAX                                                              INTEGER
                                                                        {
                                                                            false    (1),
                                                                            true     (2)
                                                                        }
    MAX-ACCESS                                                          read-write
    STATUS                                                              current
    DESCRIPTION                                                         "Indicates whether Static Port Assignment is enabled on the port."
    ::= { ntronDhcpsConfigStaticPortAssignmentsStaticPortAssignment 2}

ntronDhcpsConfigStaticPortAssignmentsStaticPortAssignmentIpAddress      OBJECT-TYPE
    SYNTAX                                                              IpAddress
    MAX-ACCESS                                                          read-write
    STATUS                                                              current
    DESCRIPTION                                                         "The IP address offer to the DHCP client connected to the port."
    ::= { ntronDhcpsConfigStaticPortAssignmentsStaticPortAssignment 3}

ntronDhcpsConfigStaticPortAssignmentsStaticPortAssignmentSubnetMask     OBJECT-TYPE
    SYNTAX                                                              IpAddress
    MAX-ACCESS                                                          read-write
    STATUS                                                              current
    DESCRIPTION                                                         "The subnet mask offer to the DHCP client connected to the port."
    ::= { ntronDhcpsConfigStaticPortAssignmentsStaticPortAssignment 4}

ntronDhcpsConfigStaticPortAssignmentsStaticPortAssignmentGateway        OBJECT-TYPE
    SYNTAX                                                              IpAddress
    MAX-ACCESS                                                          read-write
    STATUS                                                              current
    DESCRIPTION                                                         "The gateway offer to the DHCP client connected to the port."
    ::= { ntronDhcpsConfigStaticPortAssignmentsStaticPortAssignment 5}

ntronDhcpsConfigStaticPortAssignmentsStaticPortAssignmentDomain         OBJECT-TYPE
    SYNTAX                                                              DisplayString(SIZE(0..255))
    MAX-ACCESS                                                          read-write
    STATUS                                                              current
    DESCRIPTION                                                         "The domain name offer to the DHCP client connected to the port. The field is optional."
    ::= { ntronDhcpsConfigStaticPortAssignmentsStaticPortAssignment 6}

ntronDhcpsConfigStaticPortAssignmentsStaticPortAssignmentDnsOne         OBJECT-TYPE
    SYNTAX                                                              IpAddress
    MAX-ACCESS                                                          read-write
    STATUS                                                              current
    DESCRIPTION                                                         "The primary DNS offer to the DHCP client connected to the port. The field is optional."
    ::= { ntronDhcpsConfigStaticPortAssignmentsStaticPortAssignment 7}

ntronDhcpsConfigStaticPortAssignmentsStaticPortAssignmentDnsTwo         OBJECT-TYPE
    SYNTAX                                                              IpAddress
    MAX-ACCESS                                                          read-write
    STATUS                                                              current
    DESCRIPTION                                                         "The secondary DNS offer to the DHCP client connected to the port. The field is optional."
    ::= { ntronDhcpsConfigStaticPortAssignmentsStaticPortAssignment 8}

ntronDhcpsConfigStaticPortAssignmentsStaticPortAssignmentLabel          OBJECT-TYPE
    SYNTAX                                                              DisplayString(SIZE(0..32))
    MAX-ACCESS                                                          read-write
    STATUS                                                              current
    DESCRIPTION                                                         "The descriptive name of the DHCP client connected to the port. The field is optional."
    ::= { ntronDhcpsConfigStaticPortAssignmentsStaticPortAssignment 9}

ntronDhcpsConfigStaticPortAssignmentsStaticPortAssignmentPortNumberId   OBJECT-TYPE
    SYNTAX                                                              Integer32
    MAX-ACCESS                                                          read-only
    STATUS                                                              current
    DESCRIPTION                                                         "The number of the port."
    ::= {ntronDhcpsConfigStaticPortAssignmentsStaticPortAssignment 10}

ntronDhcpsConfigAlwaysIncludeClientId                                   OBJECT-TYPE
    SYNTAX                                                              INTEGER
                                                                        {
                                                                            disabled    (1),
                                                                            enabled     (2)
                                                                        }
    MAX-ACCESS                                                          read-write
    STATUS                                                              current
    DESCRIPTION                                                         "Indicates whether the DHCP Server will always respond to the client with the Client ID in the frame.
                                                                         This should be disabled for a network that is non-compliant to the RFC-6842(2013)."
    ::= { ntronDhcpsConfig 7}

--  ----------------------------------------------------------------------------------
ntronDhcpsStatus   OBJECT IDENTIFIER       ::= {ntronDhcpsGroup 20}
--  ----------------------------------------------------------------------------------

ntronDhcpsStatusLeasesTable                                     OBJECT-TYPE
    SYNTAX                                                      SEQUENCE OF NtronDhcpsStatusLeases
    MAX-ACCESS                                                  not-accessible
    STATUS                                                      current
    DESCRIPTION                                                 "Table of ntronDhcpsStatusLeasesLease entries."
    ::= { ntronDhcpsStatus 1}

ntronDhcpsStatusLeasesLease                                     OBJECT-TYPE
    SYNTAX                                                      NtronDhcpsStatusLeases
    MAX-ACCESS                                                  not-accessible
    STATUS                                                      current
    DESCRIPTION                                                 "An entry in the ntronDhcpsStatusLeasesTable."
    INDEX                                                       {ntronDhcpsStatusLeasesLeaseIndex}
    ::= { ntronDhcpsStatusLeasesTable 1 }

NtronDhcpsStatusLeases ::= SEQUENCE {
    ntronDhcpsStatusLeasesLeaseIndex                            Integer32,
    ntronDhcpsStatusLeasesLeasePoolName                         DisplayString,
    ntronDhcpsStatusLeasesLeaseBindingIdentifierStr             DisplayString,
    ntronDhcpsStatusLeasesLeaseBindingIdentifierHex             DisplayString,
    ntronDhcpsStatusLeasesLeaseMacAddress                       DisplayString,
    ntronDhcpsStatusLeasesLeaseIpAddress                        IpAddress,
    ntronDhcpsStatusLeasesLeaseStatus                           INTEGER,
    ntronDhcpsStatusLeasesLeaseRemainingLease                   DisplayString,
    ntronDhcpsStatusLeasesLeaseLabel                            DisplayString
}

ntronDhcpsStatusLeasesLeaseIndex                                OBJECT-TYPE
    SYNTAX                                                      Integer32
    MAX-ACCESS                                                  read-only
    STATUS                                                      current
    DESCRIPTION                                                 "The index of the ntronDhcpsStatusLeasesLease entry."
    ::= { ntronDhcpsStatusLeasesLease 1}

ntronDhcpsStatusLeasesLeasePoolName                             OBJECT-TYPE
    SYNTAX                                                      DisplayString(SIZE(0..20))
    MAX-ACCESS                                                  read-only
    STATUS                                                      current
    DESCRIPTION                                                 "The pool from which the lease was obtained."
    ::= { ntronDhcpsStatusLeasesLease 2}

ntronDhcpsStatusLeasesLeaseBindingIdentifierStr                 OBJECT-TYPE
    SYNTAX                                                      DisplayString(SIZE(0..255))
    MAX-ACCESS                                                  read-only
    STATUS                                                      current
    DESCRIPTION                                                 "The client associated with the lease entry in string format."
    ::= { ntronDhcpsStatusLeasesLease 3}

ntronDhcpsStatusLeasesLeaseBindingIdentifierHex                 OBJECT-TYPE
    SYNTAX                                                      DisplayString(SIZE(0..255))
    MAX-ACCESS                                                  read-only
    STATUS                                                      current
    DESCRIPTION                                                 "The client associated with the lease entry in hex format."
    ::= { ntronDhcpsStatusLeasesLease 4}

ntronDhcpsStatusLeasesLeaseMacAddress                           OBJECT-TYPE
    SYNTAX                                                      DisplayString(SIZE(0..255))
    MAX-ACCESS                                                  read-only
    STATUS                                                      current
    DESCRIPTION                                                 "Indicates the MAC address of the client associated with the lease."
    ::= { ntronDhcpsStatusLeasesLease 5}

ntronDhcpsStatusLeasesLeaseIpAddress                            OBJECT-TYPE
    SYNTAX                                                      IpAddress
    MAX-ACCESS                                                  read-only
    STATUS                                                      current
    DESCRIPTION                                                 "Indicates the IP address assigned to the lease entry."
    ::= { ntronDhcpsStatusLeasesLease 6}

ntronDhcpsStatusLeasesLeaseStatus                               OBJECT-TYPE
    SYNTAX                                                      INTEGER
                                                                {
                                                                    static      (1),
                                                                    dynamic     (2)
                                                                }
    MAX-ACCESS                                                  read-only
    STATUS                                                      current
    DESCRIPTION                                                 "Indicates the current status of the lease entry. dynamic = Assigned dynamic IP.
                                                                 static = Assigned static IP."
    ::= { ntronDhcpsStatusLeasesLease 7}

ntronDhcpsStatusLeasesLeaseRemainingLease                       OBJECT-TYPE
    SYNTAX                                                      DisplayString(SIZE(0..255))
    MAX-ACCESS                                                  read-only
    STATUS                                                      current
    DESCRIPTION                                                 "The client's remaining lease time."
    ::= { ntronDhcpsStatusLeasesLease 8}

ntronDhcpsStatusLeasesLeaseLabel                                OBJECT-TYPE
    SYNTAX                                                      DisplayString(SIZE(0..255))
    MAX-ACCESS                                                  read-only
    STATUS                                                      current
    DESCRIPTION                                                 "The descriptive name of the client."
    ::= { ntronDhcpsStatusLeasesLease 9}

--  ----------------------------------------------------------------------------------
--
--  DhcprGroup
--
--  ----------------------------------------------------------------------------------

--  ----------------------------------------------------------------------------------
ntronDhcprConfig   OBJECT IDENTIFIER       ::= {ntronDhcprGroup 10}
--  ----------------------------------------------------------------------------------

ntronDhcprConfigStatus                                          OBJECT-TYPE
    SYNTAX                                                      INTEGER
                                                                {
                                                                    disabled    (1),
                                                                    enabled     (2)
                                                                }
    MAX-ACCESS                                                  read-write
    STATUS                                                      current
    DESCRIPTION                                                 "Indicates whether the DHCP relay is active. The default is disabled."
    ::= { ntronDhcprConfig 1}

ntronDhcprConfigAgent   OBJECT IDENTIFIER     ::= {ntronDhcprConfig 2}
--  ----------------------------------------------------------------------------------
ntronDhcprConfigAgentId                                         OBJECT-TYPE
    SYNTAX                                                      DisplayString(SIZE(0..52))
    MAX-ACCESS                                                  read-write
    STATUS                                                      current
    DESCRIPTION                                                 "A unique identifier that designates this relay agent switch."
    ::= { ntronDhcprConfigAgent 1 }

ntronDhcprConfigAgentFormat                                     OBJECT-TYPE
    SYNTAX                                                      INTEGER
                                                                {
                                                                    ipAddress   (1),
                                                                    macAddress  (2),
                                                                    clientId    (3),
                                                                    otherString (4),
                                                                    otherHex    (5)
                                                                }
    MAX-ACCESS                                                  read-write
    STATUS                                                      current
    DESCRIPTION                                                 "The format selector with options for IP address, MAC Address,
                                                                 Client ID, Other String, or Other Hex characters."
    ::= {ntronDhcprConfigAgent 2}

ntronDhcprConfigServers   OBJECT IDENTIFIER     ::= {ntronDhcprConfig 3}
--  ----------------------------------------------------------------------------------

ntronDhcprConfigServersServer1                                  OBJECT-TYPE
    SYNTAX                                                      IpAddress
    MAX-ACCESS                                                  read-write
    STATUS                                                      current
    DESCRIPTION                                                 "The configured IP address of the DHCP servers."
    ::= { ntronDhcprConfigServers 1 }

ntronDhcprConfigServersServer2                                  OBJECT-TYPE
    SYNTAX                                                      IpAddress
    MAX-ACCESS                                                  read-write
    STATUS                                                      current
    DESCRIPTION                                                 "The configured IP address of the DHCP servers."
    ::= { ntronDhcprConfigServers 2 }

ntronDhcprConfigServersServer3                                  OBJECT-TYPE
    SYNTAX                                                      IpAddress
    MAX-ACCESS                                                  read-write
    STATUS                                                      current
    DESCRIPTION                                                 "The configured IP address of the DHCP servers."
    ::= { ntronDhcprConfigServers 3 }

ntronDhcprConfigServersServer4                                  OBJECT-TYPE
    SYNTAX                                                      IpAddress
    MAX-ACCESS                                                  read-write
    STATUS                                                      current
    DESCRIPTION                                                 "The configured IP address of the DHCP servers."
    ::= { ntronDhcprConfigServers 4 }

ntronDhcprConfigCircuitIdFormat                                 OBJECT-TYPE
    SYNTAX                                                      INTEGER
                                                                {
                                                                    mac     (1),
                                                                    hex     (2),
                                                                    string  (3)
                                                                }
    MAX-ACCESS                                                  read-write
    STATUS                                                      current
    DESCRIPTION                                                 "The format selector with options for MAC, Hex, and String."
    ::= { ntronDhcprConfig 4}

ntronDhcprConfigPortsTable                                      OBJECT-TYPE
    SYNTAX                                                      SEQUENCE OF NtronDhcprConfigPorts
    MAX-ACCESS                                                  not-accessible
    STATUS                                                      current
    DESCRIPTION                                                 "Table of ntronDhcprConfigPortsPort entries."
    ::= { ntronDhcprConfig 5}

ntronDhcprConfigPortsPort                                       OBJECT-TYPE
    SYNTAX                                                      NtronDhcprConfigPorts
    MAX-ACCESS                                                  not-accessible
    STATUS                                                      current
    DESCRIPTION                                                 "An entry in the ntronDhcprConfigPortsTable."
    INDEX                                                       { ntronDhcprConfigPortsPortPortNumberId }
    ::= { ntronDhcprConfigPortsTable 1 }

NtronDhcprConfigPorts ::= SEQUENCE {
    ntronDhcprConfigPortsCircuitId                              DisplayString,
    ntronDhcprConfigPortsPortPortName                           DisplayString,
    ntronDhcprConfigPortsPortEnable                             INTEGER,
    ntronDhcprConfigPortsPortPortNumberId                       Integer32
}

ntronDhcprConfigPortsCircuitId                                  OBJECT-TYPE
    SYNTAX                                                      DisplayString(SIZE(0..52))
    MAX-ACCESS                                                  read-write
    STATUS                                                      current
    DESCRIPTION                                                 "When enabled, the Circuit ID for the port can be specified.
                                                                 By default, the Circuit ID is set to the MAC Address of the port.
                                                                 Circuit IDs must be unique for each port."
    ::= { ntronDhcprConfigPortsPort 1}

ntronDhcprConfigPortsPortPortName                               OBJECT-TYPE
    SYNTAX                                                      DisplayString(SIZE(0..255))
    MAX-ACCESS                                                  read-only
    STATUS                                                      current
    DESCRIPTION                                                 "The descriptive name of the port. This field is read-only."
    ::= { ntronDhcprConfigPortsPort 2}

ntronDhcprConfigPortsPortEnable                                 OBJECT-TYPE
    SYNTAX                                                      INTEGER
                                                                {
                                                                    false    (1),
                                                                    true     (2)
                                                                }
    MAX-ACCESS                                                  read-write
    STATUS                                                      current
    DESCRIPTION                                                 "Indicates whether relay agent functionality is enabled for the port."
    ::= { ntronDhcprConfigPortsPort 3}

ntronDhcprConfigPortsPortPortNumberId                           OBJECT-TYPE
    SYNTAX                                                      Integer32
    MAX-ACCESS                                                  read-only
    STATUS                                                      current
    DESCRIPTION                                                 "The number of the port. This field is read-only."
    ::= { ntronDhcprConfigPortsPort 4}

--  ----------------------------------------------------------------------------------
--
--  LldpGroup
--
--  ----------------------------------------------------------------------------------

--  ----------------------------------------------------------------------------------
ntronLldpConfig   OBJECT IDENTIFIER       ::= {ntronLldpGroup 10}
--  ----------------------------------------------------------------------------------

ntronLldpConfigMode             OBJECT-TYPE
    SYNTAX                      INTEGER
                                {
                                    disabled    (1),
                                    enabled     (2),
                                    auto        (3)
                                }
    MAX-ACCESS                  read-write
    STATUS                      current
    DESCRIPTION                 "The LLDP mode can be Enabled, Disabled, or Auto. In Auto mode, LLDP
                                is inactive until a switch sends a wake up packet. The default is auto(3)."
    ::= { ntronLldpConfig 1}

ntronLldpConfigTransmitInterval OBJECT-TYPE
    SYNTAX                      Integer32(5..32768)
    MAX-ACCESS                  read-write
    STATUS                      current
    DESCRIPTION                 "The interval at which periodic LLDP frames are transmitted. The default is 30 seconds."
    ::= { ntronLldpConfig 2}

ntronLldpConfigTransmitHoldMultiplier   OBJECT-TYPE
    SYNTAX                              Integer32(2..10)
    MAX-ACCESS                          read-write
    STATUS                              current
    DESCRIPTION                         "A multiplier on the Transmit Interval when calculating a Time-to-Live value. The default is 4."
    ::= { ntronLldpConfig 3}

ntronLldpConfigReinitializationDelay    OBJECT-TYPE
    SYNTAX                              Integer32(1..10)
    MAX-ACCESS                          read-write
    STATUS                              current
    DESCRIPTION                         "The minimum time an LLDP port will wait before re-initializing after its setting has
                                        changed from disabled to Tx-Only or Tx/Rx. This prevents excessive notifications when
                                        LLDP Port settings are changed. The default is 2 seconds."
    ::= { ntronLldpConfig 4}

ntronLldpConfigTransmitDelay            OBJECT-TYPE
    SYNTAX                              Integer32(1..8192)
    MAX-ACCESS                          read-write
    STATUS                              current
    DESCRIPTION                         "When LLDP information is changing on the switch, the time to wait before sending an
                                        LLDP frame with the updated information. The default is 2 seconds."
    ::= { ntronLldpConfig 5}

ntronLldpConfigNotificationInterval     OBJECT-TYPE
    SYNTAX                              Integer32(5..3600)
    MAX-ACCESS                          read-write
    STATUS                              current
    DESCRIPTION                         "The interval between notifications sent by the switch. If a port sends out a notification
                                        and another port tries to send out a notification, then the subsequent notification will
                                        not be sent until the interval expires. The default is 5 seconds."
    ::= { ntronLldpConfig 6}

ntronLldpConfigPortsTable           OBJECT-TYPE
    SYNTAX                          SEQUENCE OF NtronLldpConfigPorts
    MAX-ACCESS                      not-accessible
    STATUS                          current
    DESCRIPTION                     "Table of ntronLldpConfigPortsPort entries."
    ::= { ntronLldpConfig 7}

ntronLldpConfigPortsPort                    OBJECT-TYPE
    SYNTAX                                  NtronLldpConfigPorts
    MAX-ACCESS                              not-accessible
    STATUS                                  current
    DESCRIPTION                             "An entry in the ntronLldpConfigPortsTable."
    INDEX                                   { ntronLldpConfigPortsPortNumberId }
    ::= { ntronLldpConfigPortsTable 1 }

NtronLldpConfigPorts ::= SEQUENCE {
    ntronLldpConfigPortsPortPortId              DisplayString,
    ntronLldpConfigPortsPortPortMode            INTEGER,
    ntronLldpConfigPortsPortAllowManagementData INTEGER,
    ntronLldpConfigPortsPortAllowNotification   INTEGER,
    ntronLldpConfigPortsPortPortDescription     INTEGER,
    ntronLldpConfigPortsPortSystemName          INTEGER,
    ntronLldpConfigPortsPortSystemDescription   INTEGER,
    ntronLldpConfigPortsPortSystemCapabilities  INTEGER,
    ntronLldpConfigPortsPortVlanPvid            INTEGER,
    ntronLldpConfigPortsPortVlanName            INTEGER,
    ntronLldpConfigPortsPortNumberId            Integer32
}

ntronLldpConfigPortsPortPortId          OBJECT-TYPE
    SYNTAX                              DisplayString(SIZE(0..255))
    MAX-ACCESS                          read-only
    STATUS                              current
    DESCRIPTION                         "The descriptive name of the port."
    ::= { ntronLldpConfigPortsPort 1}

ntronLldpConfigPortsPortPortMode        OBJECT-TYPE
    SYNTAX                              INTEGER
                                        {
                                            txOnly      (1),
                                            rxOnly      (2),
                                            txAndRx     (3),
                                            disabled    (4)
                                        }
    MAX-ACCESS                          read-write
    STATUS                              current
    DESCRIPTION                         "This configures whether or not LLDP frames are transmitted or received. The default is txAndRx(3)."
    ::= { ntronLldpConfigPortsPort 2}

ntronLldpConfigPortsPortAllowManagementData OBJECT-TYPE
    SYNTAX                                  INTEGER
                                            {
                                                disabled    (1),
                                                enabled     (2)
                                            }
    MAX-ACCESS                              read-write
    STATUS                                  current
    DESCRIPTION                             "Allows the transmission of management type information. Example: IP address of the switch. The default is enabled(2)."
    ::= { ntronLldpConfigPortsPort 3}

ntronLldpConfigPortsPortAllowNotification   OBJECT-TYPE
    SYNTAX                                  INTEGER
                                            {
                                                disabled    (1),
                                                enabled     (2)
                                            }
    MAX-ACCESS                              read-write
    STATUS                                  current
    DESCRIPTION                             "Allows a notification to be transmitted when local or remote data changes. The default is disabled(1)."
    ::= { ntronLldpConfigPortsPort 4}

ntronLldpConfigPortsPortPortDescription     OBJECT-TYPE
    SYNTAX                                  INTEGER
                                            {
                                                disabled    (1),
                                                enabled     (2)
                                            }
    MAX-ACCESS                              read-write
    STATUS                                  current
    DESCRIPTION                             "Indicates whether or not to send the descriptive name of the port in the transmitted LLDP frame. The default is disabled(1)."
    ::= { ntronLldpConfigPortsPort 5}

ntronLldpConfigPortsPortSystemName          OBJECT-TYPE
    SYNTAX                                  INTEGER
                                            {
                                                disabled    (1),
                                                enabled     (2)
                                            }
    MAX-ACCESS                              read-write
    STATUS                                  current
    DESCRIPTION                             "Indicates whether or not to send the name assigned to the device on the System page in the transmitted LLDP frame. The default is disabled(1)."
    ::= { ntronLldpConfigPortsPort 6}

ntronLldpConfigPortsPortSystemDescription   OBJECT-TYPE
    SYNTAX                                  INTEGER
                                            {
                                                disabled    (1),
                                                enabled     (2)
                                            }
    MAX-ACCESS                              read-write
    STATUS                                  current
    DESCRIPTION                             "Indicates whether or not to send the switch model and current firmware version in the transmitted LLDP frame. The default is disabled(1)."
    ::= { ntronLldpConfigPortsPort 7}

ntronLldpConfigPortsPortSystemCapabilities  OBJECT-TYPE
    SYNTAX                                  INTEGER
                                            {
                                                disabled    (1),
                                                enabled     (2)
                                            }
    MAX-ACCESS                              read-write
    STATUS                                  current
    DESCRIPTION                             "Indicates whether or not to send the primary function(s) of the system in the transmitted LLDP frame. The default is disabled(1)."
    ::= { ntronLldpConfigPortsPort 8}

ntronLldpConfigPortsPortVlanPvid        OBJECT-TYPE
SYNTAX                                  INTEGER
                                        {
                                            disabled    (1),
                                            enabled     (2)
                                        }
MAX-ACCESS                              read-write
STATUS                                  current
DESCRIPTION                             "Indicates whether or not to send the Port VLAN identifier (PVID) associated with the port in the transmitted LLDP frame. The default is disabled(1)"
::= { ntronLldpConfigPortsPort 9}

ntronLldpConfigPortsPortVlanName        OBJECT-TYPE
SYNTAX                                  INTEGER
                                        {
                                            disabled    (1),
                                            enabled     (2)
                                        }
MAX-ACCESS                              read-write
STATUS                                  current
DESCRIPTION                             "Indicates whether or not to send the VLAN IDs and Names assocated with the port in the transmitted LLDP Frame. The default is disabled(1)"
::= { ntronLldpConfigPortsPort 10}

ntronLldpConfigPortsPortNumberId            OBJECT-TYPE
    SYNTAX                                  Integer32
    MAX-ACCESS                              read-only
    STATUS                                  current
    DESCRIPTION                             "The port number Id."
    ::= { ntronLldpConfigPortsPort 11}

--  ----------------------------------------------------------------------------------
ntronLldpStatus   OBJECT IDENTIFIER       ::= {ntronLldpGroup 20}
--  ----------------------------------------------------------------------------------

ntronLldpStatusWakeTime     OBJECT-TYPE
    SYNTAX                  DisplayString(SIZE(0..255))
    MAX-ACCESS              read-write
    STATUS                  current
    DESCRIPTION             "The length of time LLDP will be active on switches that are in Auto mode.
                            A value of 0h0m will deactivate LLDP. Setting this OID will set the wake
                            time on all switches that are in Auto mode. The default is 0 hours and 0 minutes."
    ::= {ntronLldpStatus 1}

ntronLldpStatusNeighborsTable       OBJECT-TYPE
    SYNTAX                          SEQUENCE OF NtronLldpStatusNeighborsTable
    MAX-ACCESS                      not-accessible
    STATUS                          current
    DESCRIPTION                     "Table of ntronLldpStatusNeighborsNeighbor entries."
    ::= { ntronLldpStatus 2}

ntronLldpStatusNeighborsNeighbor    OBJECT-TYPE
    SYNTAX                          NtronLldpStatusNeighborsTable
    MAX-ACCESS                      not-accessible
    STATUS                          current
    DESCRIPTION                     "An entry in the ntronLldpStatusNeighborsTable."
    INDEX                           { ntronLldpStatusNeighborsNeighborId }
    ::= { ntronLldpStatusNeighborsTable 1 }

NtronLldpStatusNeighborsTable ::= SEQUENCE {
    ntronLldpStatusNeighborsNeighborId                  Integer32,
    ntronLldpStatusNeighborsNeighborLocalPortNumber     DisplayString,
    ntronLldpStatusNeighborsNeighborMacAddress          DisplayString,
    ntronLldpStatusNeighborsNeighborPortId              DisplayString,
    ntronLldpStatusNeighborsNeighborIpAddress           IpAddress,
    ntronLldpStatusNeighborsNeighborPortDescription     DisplayString,
    ntronLldpStatusNeighborsNeighborSystemName          DisplayString,
    ntronLldpStatusNeighborsNeighborPvid                Integer32,
    ntronLldpStatusNeighborsNeighborTtl                 Integer32,
    ntronLldpStatusNeighborsNeighborLocalPortNumberId   Integer32
}

ntronLldpStatusNeighborsNeighborId      OBJECT-TYPE
    SYNTAX                              Integer32
    MAX-ACCESS                          read-only
    STATUS                              current
    DESCRIPTION                         "The Neighbor Id."
    ::= {ntronLldpStatusNeighborsNeighbor 1}

ntronLldpStatusNeighborsNeighborLocalPortNumber     OBJECT-TYPE
    SYNTAX                                          DisplayString(SIZE(0..255))
    MAX-ACCESS                                      read-only
    STATUS                                          current
    DESCRIPTION                                     "The local port number"
    ::= {ntronLldpStatusNeighborsNeighbor 2}

ntronLldpStatusNeighborsNeighborMacAddress  OBJECT-TYPE
    SYNTAX                                  DisplayString(SIZE(0..255))
    MAX-ACCESS                              read-only
    STATUS                                  current
    DESCRIPTION                             "MAC address of neighbor device. Corresponds to the LLDP Chassis ID TLV."
    ::= {ntronLldpStatusNeighborsNeighbor 3}

ntronLldpStatusNeighborsNeighborPortId      OBJECT-TYPE
    SYNTAX                                  DisplayString(SIZE(0..255))
    MAX-ACCESS                              read-only
    STATUS                                  current
    DESCRIPTION                             "Identifier of the neighbor port from which the LLDP frame was sent."
    ::= {ntronLldpStatusNeighborsNeighbor 4}

ntronLldpStatusNeighborsNeighborIpAddress   OBJECT-TYPE
    SYNTAX                                  IpAddress
    MAX-ACCESS                              read-only
    STATUS                                  current
    DESCRIPTION                             "IP address of neighbor device. Corresponds to the LLDP Management Address TLV."
    ::= {ntronLldpStatusNeighborsNeighbor 5}

ntronLldpStatusNeighborsNeighborPortDescription OBJECT-TYPE
    SYNTAX                                      DisplayString(SIZE(0..255))
    MAX-ACCESS                                  read-only
    STATUS                                      current
    DESCRIPTION                                 "Description of the neighbor port from which the LLDP frame was sent."
    ::= {ntronLldpStatusNeighborsNeighbor 6}

ntronLldpStatusNeighborsNeighborSystemName  OBJECT-TYPE
    SYNTAX                                  DisplayString(SIZE(0..255))
    MAX-ACCESS                              read-only
    STATUS                                  current
    DESCRIPTION                             "The system's administratively assigned name on the neighbor device."
    ::= {ntronLldpStatusNeighborsNeighbor 7}

ntronLldpStatusNeighborsNeighborPvid        OBJECT-TYPE
    SYNTAX                                  Integer32
    MAX-ACCESS                              read-only
    STATUS                                  current
    DESCRIPTION                             ""
    ::= {ntronLldpStatusNeighborsNeighbor 8}

ntronLldpStatusNeighborsNeighborTtl         OBJECT-TYPE
    SYNTAX                                  Integer32
    MAX-ACCESS                              read-only
    STATUS                                  current
    DESCRIPTION                             "Indicates the number of seconds that the information associated with this neighbor will be valid. Time to Live (TTL)."
    ::= {ntronLldpStatusNeighborsNeighbor 9}

ntronLldpStatusNeighborsNeighborLocalPortNumberId    OBJECT-TYPE
    SYNTAX                                          Integer32
    MAX-ACCESS                                      read-only
    STATUS                                          current
    DESCRIPTION                                     "The local port number Id."
    ::= {ntronLldpStatusNeighborsNeighbor 10}

ntronLldpStatusNeighborsVlanTable   OBJECT-TYPE
    SYNTAX                          SEQUENCE OF NtronLldpStatusNeighborsVlanTable
    MAX-ACCESS                      not-accessible
    STATUS                          current
    DESCRIPTION                     "Table of ntronLldpStatusNeighborsNeighbor entries."
    ::= { ntronLldpStatus 3}

ntronLldpStatusNeighborsVlanNeighbor    OBJECT-TYPE
    SYNTAX                              NtronLldpStatusNeighborsVlanTable
    MAX-ACCESS                          not-accessible
    STATUS                              current
    DESCRIPTION                         "An entry in the ntronLldpStatusNeighborsTable."
    INDEX                               { ntronLldpStatusNeighborsVlanNeighborVlanId }
    ::= { ntronLldpStatusNeighborsVlanTable 1 }

NtronLldpStatusNeighborsVlanTable ::= SEQUENCE {
    ntronLldpStatusNeighborsVlanNeighborVlanLocalPortNumber DisplayString,
    ntronLldpStatusNeighborsVlanNeighborVlanMacAddress      DisplayString,
    ntronLldpStatusNeighborsVlanNeighborVlanId              DisplayString,
    ntronLldpStatusNeighborsVlanNeighborVlanName            DisplayString,
    ntronLldpStatusNeighborsNeighborIndex                   INTEGER
}

ntronLldpStatusNeighborsVlanNeighborVlanLocalPortNumber     OBJECT-TYPE
    SYNTAX                                                  DisplayString(SIZE(0..255))
    MAX-ACCESS                                              read-only
    STATUS                                                  current
    DESCRIPTION                                             "The local port number"
    ::= {ntronLldpStatusNeighborsVlanNeighbor 1}

ntronLldpStatusNeighborsVlanNeighborVlanMacAddress  OBJECT-TYPE
    SYNTAX                                          DisplayString(SIZE(0..255))
    MAX-ACCESS                                      read-only
    STATUS                                          current
    DESCRIPTION                                     "MAC address of neighbor device. Corresponds to the LLDP Chassis ID TLV."
    ::= {ntronLldpStatusNeighborsVlanNeighbor 2}

ntronLldpStatusNeighborsVlanNeighborVlanName    OBJECT-TYPE
    SYNTAX                                      DisplayString(SIZE(0..255))
    MAX-ACCESS                                  read-only
    STATUS                                      current
    DESCRIPTION                                 "VLAN Name of the neighbor port from which the LLDP frame was sent."
    ::= {ntronLldpStatusNeighborsVlanNeighbor 3}

ntronLldpStatusNeighborsVlanNeighborVlanId  OBJECT-TYPE
    SYNTAX                                  DisplayString(SIZE(0..255))
    MAX-ACCESS                              read-only
    STATUS                                  current
    DESCRIPTION                             "VLAN Name of the neighbor port from which the LLDP frame was sent."
    ::= {ntronLldpStatusNeighborsVlanNeighbor 4}

ntronLldpStatusNeighborsNeighborIndex           OBJECT-TYPE
    SYNTAX                                      INTEGER
    MAX-ACCESS                                  read-only
    STATUS                                      current
    DESCRIPTION                                 "The index to the VLAN."
    ::= {ntronLldpStatusNeighborsVlanNeighbor 5}

ntronLldpStatusPortsStatsTable                      OBJECT-TYPE
    SYNTAX                                          SEQUENCE OF NtronLldpStatusPortsStatsTable
    MAX-ACCESS                                      not-accessible
    STATUS                                          current
    DESCRIPTION                                     "Table of ntronLldpStatusPortsStatPort entries."
    ::= { ntronLldpStatus 4}

ntronLldpStatusPortsStatPort                        OBJECT-TYPE
    SYNTAX                                          NtronLldpStatusPortsStatsTable
    MAX-ACCESS                                      not-accessible
    STATUS                                          current
    DESCRIPTION                                     "An entry in the ntronLldpStatusPortsStatsTable."
    INDEX                                           { ntronPortsStatusPortPortNumberId }
    ::= { ntronLldpStatusPortsStatsTable 1 }

NtronLldpStatusPortsStatsTable ::= SEQUENCE {
    ntronLldpStatusPortsStatPortNumber              DisplayString,
    ntronLldpStatusPortsStatPortTransmitFrames      Integer32,
    ntronLldpStatusPortsStatPortReceivedFrames      Integer32,
    ntronLldpStatusPortsStatPortDiscardedFrames     Integer32,
    ntronLldpStatusPortsStatPortErrorFrames         Integer32,
    ntronLldpStatusPortsStatPortDiscardedTlvs       Integer32,
    ntronLldpStatusPortsStatPortUnrecognizedTlvs    Integer32,
    ntronLldpStatusPortsStatPortAgeOut              Integer32,
    ntronLldpStatusPortsStatPortNumberId            Integer32
}

ntronLldpStatusPortsStatPortNumber  OBJECT-TYPE
    SYNTAX                          DisplayString(SIZE(0..255))
    MAX-ACCESS                      read-only
    STATUS                          current
    DESCRIPTION                     "The port number"
    ::= {ntronLldpStatusPortsStatPort 1}

ntronLldpStatusPortsStatPortTransmitFrames  OBJECT-TYPE
    SYNTAX                                  Integer32
    MAX-ACCESS                              read-only
    STATUS                                  current
    DESCRIPTION                             "The total number of LLDP frames transmitted by the local switch."
    ::= {ntronLldpStatusPortsStatPort 2}

ntronLldpStatusPortsStatPortReceivedFrames  OBJECT-TYPE
    SYNTAX                                  Integer32
    MAX-ACCESS                              read-only
    STATUS                                  current
    DESCRIPTION                             "Total number of LLDP frames received by the local switch."
    ::= {ntronLldpStatusPortsStatPort 3}

ntronLldpStatusPortsStatPortDiscardedFrames OBJECT-TYPE
    SYNTAX                                  Integer32
    MAX-ACCESS                              read-only
    STATUS                                  current
    DESCRIPTION                             "The total number of frames discarded due to incorrect Type Length Values (TLVs) in the frames."
    ::= {ntronLldpStatusPortsStatPort 4}

ntronLldpStatusPortsStatPortErrorFrames     OBJECT-TYPE
    SYNTAX                                  Integer32
    MAX-ACCESS                              read-only
    STATUS                                  current
    DESCRIPTION                             "Total count of all LLDP frames received with one or more errors."
    ::= {ntronLldpStatusPortsStatPort 5}

ntronLldpStatusPortsStatPortDiscardedTlvs   OBJECT-TYPE
    SYNTAX                                  Integer32
    MAX-ACCESS                              read-only
    STATUS                                  current
    DESCRIPTION                             "The count of all TLVs discarded for any reason."
    ::= {ntronLldpStatusPortsStatPort 6}

ntronLldpStatusPortsStatPortUnrecognizedTlvs    OBJECT-TYPE
    SYNTAX                                      Integer32
    MAX-ACCESS                                  read-only
    STATUS                                      current
    DESCRIPTION                                 "The count of all TLVs received on the port that are not recognized by LLDP."
    ::= {ntronLldpStatusPortsStatPort 7}

ntronLldpStatusPortsStatPortAgeOut  OBJECT-TYPE
    SYNTAX                          Integer32
    MAX-ACCESS                      read-only
    STATUS                          current
    DESCRIPTION                     "The count of times that a neighbor's information has been deleted because it's Time To Live (TTL) has expired."
    ::= {ntronLldpStatusPortsStatPort 8}

ntronLldpStatusPortsStatPortNumberId    OBJECT-TYPE
    SYNTAX                              Integer32
    MAX-ACCESS                          read-only
    STATUS                              current
    DESCRIPTION                         "The port number Id."
    ::= {ntronLldpStatusPortsStatPort 9}
END
